-- *********************************************************************
-- CISCO-UNIFIED-COMPUTING-FABRIC-MIB.my
-- 
-- MIB representation of the Cisco Unified Computing System
-- FABRIC management information model package
-- 
-- Created September 2011 by Charles Bullis
-- 
-- Copyright (c) 2005-2011 Cisco Systems, Inc. All rights reserved.
-- 
-- *********************************************************************

CISCO-UNIFIED-COMPUTING-FABRIC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsComputeDiscovery,
    CucsConditionRemoteInvRslt,
    CucsEquipmentConnectionStatus,
    CucsEquipmentFabricEpType,
    CucsEquipmentSlotStatus,
    CucsFabricADceSwSrvEpTransport,
    CucsFabricAEthEstcEpIfRole,
    CucsFabricAEthEstcEpTransport,
    CucsFabricAEthEstcEpType,
    CucsFabricAEthLanEpTransport,
    CucsFabricAFcEstcEpTransport,
    CucsFabricAFcEstcEpType,
    CucsFabricAFcSanEpTransport,
    CucsFabricAFcoeEstcEpIfRole,
    CucsFabricAFcoeEstcEpTransport,
    CucsFabricAFcoeEstcEpType,
    CucsFabricAVlanSharing,
    CucsFabricAVlanTransport,
    CucsFabricAVlanType,
    CucsFabricAVsanTransport,
    CucsFabricAVsanType,
    CucsFabricAdminState,
    CucsFabricBHVlanSwitchId,
    CucsFabricBladeLifeCycle,
    CucsFabricCIoEpIfType,
    CucsFabricComputeEpIfRole,
    CucsFabricComputeEpType,
    CucsFabricComputeSlotEpFsmTaskItem,
    CucsFabricComputeSlotEpSlotId,
    CucsFabricConfMode,
    CucsFabricConfigState,
    CucsFabricDceSwSrvEpPortId,
    CucsFabricDceSwSrvEpSlotId,
    CucsFabricDceSwSrvPcEpPortId,
    CucsFabricDceSwSrvPcEpSlotId,
    CucsFabricDceSwSrvPcPortId,
    CucsFabricDceSwSrvPcTransport,
    CucsFabricDefaultZoningState,
    CucsFabricEpMgrFsmTaskFlags,
    CucsFabricEpMgrFsmTaskItem,
    CucsFabricEstcEpIfRole,
    CucsFabricEstcPcIfRole,
    CucsFabricEstcPcType,
    CucsFabricEthEstcEpPortId,
    CucsFabricEthEstcEpPrio,
    CucsFabricEthEstcEpSlotId,
    CucsFabricEthEstcEpTransport,
    CucsFabricEthEstcEpType,
    CucsFabricEthEstcPcEpPortId,
    CucsFabricEthEstcPcEpSlotId,
    CucsFabricEthEstcPcTransport,
    CucsFabricEthEstcPortMode,
    CucsFabricEthEstcTransport,
    CucsFabricEthEstcType,
    CucsFabricEthLanPcTransport,
    CucsFabricEthLanTransport,
    CucsFabricEthMonDestEpIfRole,
    CucsFabricEthMonDestEpPortId,
    CucsFabricEthMonDestEpSlotId,
    CucsFabricEthMonDestEpType,
    CucsFabricEthMonFiltEpType,
    CucsFabricEthMonFiltRefType,
    CucsFabricEthMonLanTransport,
    CucsFabricEthMonLanType,
    CucsFabricEthMonSrcEpType,
    CucsFabricEthMonSrcRefType,
    CucsFabricEthMonTransport,
    CucsFabricEthMonType,
    CucsFabricEthPcProtocol,
    CucsFabricEthSourceType,
    CucsFabricEthTargetEpTransport,
    CucsFabricEthVlanPcTransport,
    CucsFabricExternalEpAdminState,
    CucsFabricExternalEpLocale,
    CucsFabricExternalLocale,
    CucsFabricExternalPcLocale,
    CucsFabricFcEstcEpPortId,
    CucsFabricFcEstcEpSlotId,
    CucsFabricFcEstcTransport,
    CucsFabricFcEstcType,
    CucsFabricFcMonDestEpIfRole,
    CucsFabricFcMonDestEpPortId,
    CucsFabricFcMonDestEpSlotId,
    CucsFabricFcMonDestEpType,
    CucsFabricFcMonFiltEpType,
    CucsFabricFcMonFiltRefType,
    CucsFabricFcMonSanTransport,
    CucsFabricFcMonSanType,
    CucsFabricFcMonSrcEpType,
    CucsFabricFcMonSrcRefType,
    CucsFabricFcMonTransport,
    CucsFabricFcMonType,
    CucsFabricFcSanEpPortId,
    CucsFabricFcSanEpSlotId,
    CucsFabricFcSanPcEpPortId,
    CucsFabricFcSanPcEpSlotId,
    CucsFabricFcSanPcTransport,
    CucsFabricFcSanTransport,
    CucsFabricFcSanUplinkTrunking,
    CucsFabricFcSourceType,
    CucsFabricFcVsanPcTransport,
    CucsFabricFcVsanPortEpPortId,
    CucsFabricFcVsanPortEpSlotId,
    CucsFabricFcoeEstcEpPortId,
    CucsFabricFcoeEstcEpSlotId,
    CucsFabricFcoeVsanPortEpPortId,
    CucsFabricFcoeVsanPortEpSlotId,
    CucsFabricInternalDceSrvTransport,
    CucsFabricInternalDceSrvType,
    CucsFabricInternalEpAdminState,
    CucsFabricInternalEpLocale,
    CucsFabricInternalLocale,
    CucsFabricInternalPcLocale,
    CucsFabricLanCloudFsmTaskItem,
    CucsFabricLanEpIfRole,
    CucsFabricLanEpType,
    CucsFabricLanPcIfRole,
    CucsFabricLanPcType,
    CucsFabricLanType,
    CucsFabricLifeCycle,
    CucsFabricMembershipStatus,
    CucsFabricMonAdminState,
    CucsFabricMonOperState,
    CucsFabricMonOperStateReason,
    CucsFabricPIoEpIfType,
    CucsFabricPIoEpPortId,
    CucsFabricPIoEpSlotId,
    CucsFabricPathEpIfType,
    CucsFabricPathEpLocale,
    CucsFabricPcConfigStatus,
    CucsFabricSanCloudFsmTaskItem,
    CucsFabricSanEpIfRole,
    CucsFabricSanEpType,
    CucsFabricSanPcIfRole,
    CucsFabricSanPcType,
    CucsFabricSanType,
    CucsFabricSlotAdminState,
    CucsFabricSwChEpIfRole,
    CucsFabricSwChEpType,
    CucsFabricSwSrvEpIfRole,
    CucsFabricSwSrvEpType,
    CucsFabricSwSrvPcIfRole,
    CucsFabricSwSrvPcType,
    CucsFabricSwitchingMode,
    CucsFabricTargetEpType,
    CucsFabricTrafficDirection,
    CucsFabricVConPlacementPref,
    CucsFabricVConSelectPref,
    CucsFabricVConSharePref,
    CucsFabricVConTransportPref,
    CucsFabricVlanOperState,
    CucsFabricVlanSwitchId,
    CucsFabricVnetEpIfRole,
    CucsFabricVnetEpLocale,
    CucsFabricVsanOperState,
    CucsFabricVsanSwitchId,
    CucsFsmCompletion,
    CucsFsmFlags,
    CucsLicenseState,
    CucsNetworkConnectionType,
    CucsNetworkLocale,
    CucsNetworkPortOperState,
    CucsNetworkPortRole,
    CucsNetworkSide,
    CucsNetworkSwitchId,
    CucsNetworkTransport,
    CucsNetworkVnetEpIfType,
    CucsPortEthSpeed,
    CucsPortSpeed,
    CucsQosPriority
        FROM CISCO-UNIFIED-COMPUTING-TC-MIB;

cucsFabricObjects MODULE-IDENTITY
    LAST-UPDATED    "201109150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        FABRIC management information model package"
    ::= { ciscoUnifiedComputingMIBObjects 19 }

cucsFabricBHVlanTable OBJECT-TYPE
    SYNTAX           SEQUENCE OF CucsFabricBHVlanEntry
    MAX-ACCESS       not-accessible
    STATUS           current
    DESCRIPTION
        "Cisco UCS fabric:BHVlan managed object table"
    ::= { cucsFabricObjects 66 }

cucsFabricBHVlanEntry OBJECT-TYPE
    SYNTAX           CucsFabricBHVlanEntry
    MAX-ACCESS       not-accessible
    STATUS           current
    DESCRIPTION
        "Entry for the cucsFabricBHVlanTable table."
    INDEX { cucsFabricBHVlanInstanceId }
    ::= { cucsFabricBHVlanTable 1 }

CucsFabricBHVlanEntry ::= SEQUENCE {
    cucsFabricBHVlanInstanceId                                       CucsManagedObjectId,
    cucsFabricBHVlanDn                                               CucsManagedObjectDn,
    cucsFabricBHVlanRn                                               SnmpAdminString,
    cucsFabricBHVlanEpDn                                             SnmpAdminString,
    cucsFabricBHVlanId                                               Gauge32,
    cucsFabricBHVlanIfRole                                           CucsFabricVnetEpIfRole,
    cucsFabricBHVlanIfType                                           CucsNetworkVnetEpIfType,
    cucsFabricBHVlanLocale                                           CucsFabricVnetEpLocale,
    cucsFabricBHVlanName                                             SnmpAdminString,
    cucsFabricBHVlanPeerDn                                           SnmpAdminString,
    cucsFabricBHVlanPubNwDn                                          SnmpAdminString,
    cucsFabricBHVlanPubNwId                                          Gauge32,
    cucsFabricBHVlanPubNwName                                        SnmpAdminString,
    cucsFabricBHVlanSharing                                          CucsFabricAVlanSharing,
    cucsFabricBHVlanSwitchId                                         CucsFabricBHVlanSwitchId,
    cucsFabricBHVlanTransport                                        CucsFabricAVlanTransport,
    cucsFabricBHVlanType                                             CucsFabricAVlanType,
    cucsFabricBHVlanOperState                                        CucsFabricVlanOperState
}

cucsFabricBHVlanInstanceId OBJECT-TYPE
    SYNTAX       CucsManagedObjectId
    MAX-ACCESS   not-accessible
    STATUS       current
    DESCRIPTION
        "Instance identifier of the managed object."
    ::= { cucsFabricBHVlanEntry 1 }

cucsFabricBHVlanDn OBJECT-TYPE
    SYNTAX       CucsManagedObjectDn
    MAX-ACCESS   read-only
    STATUS       current
    DESCRIPTION
        "Cisco UCS fabric:BHVlan:dn managed object property"
    ::= { cucsFabricBHVlanEntry 2 }

cucsFabricBHVlanRn OBJECT-TYPE
    SYNTAX       SnmpAdminString
    MAX-ACCESS   read-only
    STATUS       current
    DESCRIPTION
        "Cisco UCS fabric:BHVlan:rn managed object property"
    ::= { cucsFabricBHVlanEntry 3 }

cucsFabricBHVlanEpDn OBJECT-TYPE
    SYNTAX       SnmpAdminString
    MAX-ACCESS   read-only
    STATUS       current
    DESCRIPTION
        "Cisco UCS fabric:BHVlan:epDn managed object property"
    ::= { cucsFabricBHVlanEntry 4 }

cucsFabricBHVlanId OBJECT-TYPE
    SYNTAX       Gauge32
    MAX-ACCESS   read-only
    STATUS       current
    DESCRIPTION
        "Cisco UCS fabric:BHVlan:id managed object property"
    ::= { cucsFabricBHVlanEntry 5 }

cucsFabricBHVlanIfRole OBJECT-TYPE
    SYNTAX       CucsFabricVnetEpIfRole
    MAX-ACCESS   read-only
    STATUS       current
    DESCRIPTION
        "Cisco UCS fabric:BHVlan:ifRole managed object property"
    ::= { cucsFabricBHVlanEntry 6 }

cucsFabricBHVlanIfType OBJECT-TYPE
    SYNTAX       CucsNetworkVnetEpIfType
    MAX-ACCESS   read-only
    STATUS       current
    DESCRIPTION
        "Cisco UCS fabric:BHVlan:ifType managed object property"
    ::= { cucsFabricBHVlanEntry 7 }

cucsFabricBHVlanLocale OBJECT-TYPE
    SYNTAX       CucsFabricVnetEpLocale
    MAX-ACCESS   read-only
    STATUS       current
    DESCRIPTION
        "Cisco UCS fabric:BHVlan:locale managed object property"
    ::= { cucsFabricBHVlanEntry 8 }

cucsFabricBHVlanName OBJECT-TYPE
    SYNTAX       SnmpAdminString
    MAX-ACCESS   read-only
    STATUS       current
    DESCRIPTION
        "Cisco UCS fabric:BHVlan:name managed object property"
    ::= { cucsFabricBHVlanEntry 9 }

cucsFabricBHVlanPeerDn OBJECT-TYPE
    SYNTAX       SnmpAdminString
    MAX-ACCESS   read-only
    STATUS       current
    DESCRIPTION
        "Cisco UCS fabric:BHVlan:peerDn managed object property"
    ::= { cucsFabricBHVlanEntry 10 }

cucsFabricBHVlanPubNwDn OBJECT-TYPE
    SYNTAX       SnmpAdminString
    MAX-ACCESS   read-only
    STATUS       current
    DESCRIPTION
        "Cisco UCS fabric:BHVlan:pubNwDn managed object property"
    ::= { cucsFabricBHVlanEntry 11 }

cucsFabricBHVlanPubNwId OBJECT-TYPE
    SYNTAX       Gauge32
    MAX-ACCESS   read-only
    STATUS       current
    DESCRIPTION
        "Cisco UCS fabric:BHVlan:pubNwId managed object property"
    ::= { cucsFabricBHVlanEntry 12 }

cucsFabricBHVlanPubNwName OBJECT-TYPE
    SYNTAX       SnmpAdminString
    MAX-ACCESS   read-only
    STATUS       current
    DESCRIPTION
        "Cisco UCS fabric:BHVlan:pubNwName managed object property"
    ::= { cucsFabricBHVlanEntry 13 }

cucsFabricBHVlanSharing OBJECT-TYPE
    SYNTAX       CucsFabricAVlanSharing
    MAX-ACCESS   read-only
    STATUS       current
    DESCRIPTION
        "Cisco UCS fabric:BHVlan:sharing managed object property"
    ::= { cucsFabricBHVlanEntry 14 }

cucsFabricBHVlanSwitchId OBJECT-TYPE
    SYNTAX       CucsFabricBHVlanSwitchId
    MAX-ACCESS   read-only
    STATUS       current
    DESCRIPTION
        "Cisco UCS fabric:BHVlan:switchId managed object property"
    ::= { cucsFabricBHVlanEntry 15 }

cucsFabricBHVlanTransport OBJECT-TYPE
    SYNTAX       CucsFabricAVlanTransport
    MAX-ACCESS   read-only
    STATUS       current
    DESCRIPTION
        "Cisco UCS fabric:BHVlan:transport managed object property"
    ::= { cucsFabricBHVlanEntry 16 }

cucsFabricBHVlanType OBJECT-TYPE
    SYNTAX       CucsFabricAVlanType
    MAX-ACCESS   read-only
    STATUS       current
    DESCRIPTION
        "Cisco UCS fabric:BHVlan:type managed object property"
    ::= { cucsFabricBHVlanEntry 17 }

cucsFabricBHVlanOperState OBJECT-TYPE
    SYNTAX       CucsFabricVlanOperState
    MAX-ACCESS   read-only
    STATUS       current
    DESCRIPTION
        "Cisco UCS fabric:BHVlan:operState managed object property"
    ::= { cucsFabricBHVlanEntry 18 }

cucsFabricChassisEpTable OBJECT-TYPE
    SYNTAX           SEQUENCE OF CucsFabricChassisEpEntry
    MAX-ACCESS       not-accessible
    STATUS           current
    DESCRIPTION
        "Cisco UCS fabric:ChassisEp managed object table"
    ::= { cucsFabricObjects 1 }

cucsFabricChassisEpEntry OBJECT-TYPE
    SYNTAX           CucsFabricChassisEpEntry
    MAX-ACCESS       not-accessible
    STATUS           current
    DESCRIPTION
        "Entry for the cucsFabricChassisEpTable table."
    INDEX { cucsFabricChassisEpInstanceId }
    ::= { cucsFabricChassisEpTable 1 }

CucsFabricChassisEpEntry ::= SEQUENCE {
    cucsFabricChassisEpInstanceId                                    CucsManagedObjectId,
    cucsFabricChassisEpDn                                            CucsManagedObjectDn,
    cucsFabricChassisEpRn                                            SnmpAdminString,
    cucsFabricChassisEpAdminState                                    CucsFabricInternalEpAdminState,
    cucsFabricChassisEpChassisDn                                     SnmpAdminString,
    cucsFabricChassisEpChassisId                                     Gauge32,
    cucsFabricChassisEpEpDn                                          SnmpAdminString,
    cucsFabricChassisEpIfRole                                        CucsFabricComputeEpIfRole,
    cucsFabricChassisEpIfType                                        CucsFabricPIoEpIfType,
    cucsFabricChassisEpLicGP                                         Unsigned64,
    cucsFabricChassisEpLicState                                      CucsLicenseState,
    cucsFabricChassisEpLocale                                        CucsFabricInternalEpLocale,
    cucsFabricChassisEpModel                                         SnmpAdminString,
    cucsFabricChassisEpName                                          SnmpAdminString,
    cucsFabricChassisEpPeerDn                                        SnmpAdminString,
    cucsFabricChassisEpPeerPortId                                    Gauge32,
    cucsFabricChassisEpPeerSlotId                                    Gauge32,
    cucsFabricChassisEpPortId                                        CucsFabricPIoEpPortId,
    cucsFabricChassisEpRevision                                      SnmpAdminString,
    cucsFabricChassisEpSerial                                        SnmpAdminString,
    cucsFabricChassisEpSlotId                                        CucsFabricPIoEpSlotId,
    cucsFabricChassisEpSwitchId                                      CucsNetworkSwitchId,
    cucsFabricChassisEpTransport                                     CucsNetworkTransport,
    cucsFabricChassisEpType                                          CucsFabricComputeEpType,
    cucsFabricChassisEpVendor                                        SnmpAdminString,
    cucsFabricChassisEpPeerChassisId                                 Gauge32,
    cucsFabricChassisEpFltAggr                                       Unsigned64
}

cucsFabricChassisEpInstanceId OBJECT-TYPE
    SYNTAX       CucsManagedObjectId
    MAX-ACCESS   not-accessible
    STATUS       current
    DESCRIPTION
        "Instance identifier of the managed object."
    ::= { cucsFabricChassisEpEntry 1 }

cucsFabricChassisEpDn OBJECT-TYPE
    SYNTAX       CucsManagedObjectDn
    MAX-ACCESS   read-only
    STATUS       current
    DESCRIPTION
        "Cisco UCS fabric:ChassisEp:dn managed object property"
    ::= { cucsFabricChassisEpEntry 2 }

cucsFabricChassisEpRn OBJECT-TYPE
    SYNTAX       SnmpAdminString
    MAX-ACCESS   read-only
    STATUS       current
    DESCRIPTION
        "Cisco UCS fabric:ChassisEp:rn managed object property"
    ::= { cucsFabricChassisEpEntry 3 }

cucsFabricChassisEpAdminState OBJECT-TYPE
    SYNTAX       CucsFabricInternalEpAdminState
    MAX-ACCESS   read-only
    STATUS       current
    DESCRIPTION
        "Cisco UCS fabric:ChassisEp:adminState managed object property"
    ::= { cucsFabricChassisEpEntry 4 }

cucsFabricChassisEpChassisDn OBJECT-TYPE
    SYNTAX       SnmpAdminString
    MAX-ACCESS   read-only
    STATUS       current
    DESCRIPTION
        "Cisco UCS fabric:ChassisEp:chassisDn managed object property"
    ::= { cucsFabricChassisEpEntry 5 }

cucsFabricChassisEpChassisId OBJECT-TYPE
    SYNTAX       Gauge32
    MAX-ACCESS   read-only
    STATUS       current
    DESCRIPTION
        "Cisco UCS fabric:ChassisEp:chassisId managed object property"
    ::= { cucsFabricChassisEpEntry 6 }

cucsFabricChassisEpEpDn OBJECT-TYPE
    SYNTAX       SnmpAdminString
    MAX-ACCESS   read-only
    STATUS       current
    DESCRIPTION
        "Cisco UCS fabric:ChassisEp:epDn managed object property"
    ::= { cucsFabricChassisEpEntry 7 }

cucsFabricChassisEpIfRole OBJECT-TYPE
    SYNTAX       CucsFabricComputeEpIfRole
    MAX-ACCESS   read-only
    STATUS       current
    DESCRIPTION
        "Cisco UCS fabric:ChassisEp:ifRole managed object property"
    ::= { cucsFabricChassisEpEntry 8 }

cucsFabricChassisEpIfType OBJECT-TYPE
    SYNTAX       CucsFabricPIoEpIfType
    MAX-ACCESS   read-only
    STATUS       current
    DESCRIPTION
        "Cisco UCS fabric:ChassisEp:ifType managed object property"
    ::= { cucsFabricChassisEpEntry 9 }

cucsFabricChassisEpLicGP OBJECT-TYPE
    SYNTAX       Unsigned64
    MAX-ACCESS   read-only
    STATUS       current
    DESCRIPTION
        "Cisco UCS fabric:ChassisEp:licGP managed object property"
    ::= { cucsFabricChassisEpEntry 10 }

cucsFabricChassisEpLicState OBJECT-TYPE
    SYNTAX       CucsLicenseState
    MAX-ACCESS   read-only
    STATUS       current
    DESCRIPTION
        "Cisco UCS fabric:ChassisEp:licState managed object property"
    ::= { cucsFabricChassisEpEntry 11 }

cucsFabricChassisEpLocale OBJECT-TYPE
    SYNTAX       CucsFabricInternalEpLocale
    MAX-ACCESS   read-only
    STATUS       current
    DESCRIPTION
        "Cisco UCS fabric:ChassisEp:locale managed object property"
    ::= { cucsFabricChassisEpEntry 12 }

cucsFabricChassisEpModel OBJECT-TYPE
    SYNTAX       SnmpAdminString
    MAX-ACCESS   read-only
    STATUS       current
    DESCRIPTION
        "Cisco UCS fabric:ChassisEp:model managed object property"
    ::= { cucsFabricChassisEpEntry 13 }

cucsFabricChassisEpName OBJECT-TYPE
    SYNTAX       SnmpAdminString
    MAX-ACCESS   read-only
    STATUS       current
    DESCRIPTION
        "Cisco UCS fabric:ChassisEp:name managed object property"
    ::= { cucsFabricChassisEpEntry 14 }

cucsFabricChassisEpPeerDn OBJECT-TYPE
    SYNTAX       SnmpAdminString
    MAX-ACCESS   read-only
    STATUS       current
    DESCRIPTION
        "Cisco UCS fabric:ChassisEp:peerDn managed object property"
    ::= { cucsFabricChassisEpEntry 15 }

cucsFabricChassisEpPeerPortId OBJECT-TYPE
    SYNTAX       Gauge32
    MAX-ACCESS   read-only
    STATUS       current
    DESCRIPTION
        "Cisco UCS fabric:ChassisEp:peerPortId managed object property"
    ::= { cucsFabricChassisEpEntry 16 }

cucsFabricChassisEpPeerSlotId OBJECT-TYPE
    SYNTAX       Gauge32
    MAX-ACCESS   read-only
    STATUS       current
    DESCRIPTION
        "Cisco UCS fabric:ChassisEp:peerSlotId managed object property"
    ::= { cucsFabricChassisEpEntry 17 }

cucsFabricChassisEpPortId OBJECT-TYPE
    SYNTAX       CucsFabricPIoEpPortId
    MAX-ACCESS   read-only
    STATUS       current
    DESCRIPTION
        "Cisco UCS fabric:ChassisEp:portId managed object property"
    ::= { cucsFabricChassisEpEntry 18 }

cucsFabricChassisEpRevision OBJECT-TYPE
    SYNTAX       SnmpAdminString
    MAX-ACCESS   read-only
    STATUS       current
    DESCRIPTION
        "Cisco UCS fabric:ChassisEp:revision managed object property"
    ::= { cucsFabricChassisEpEntry 19 }

cucsFabricChassisEpSerial OBJECT-TYPE
    SYNTAX       SnmpAdminString
    MAX-ACCESS   read-only
    STATUS       current
    DESCRIPTION
        "Cisco UCS fabric:ChassisEp:serial managed object property"
    ::= { cucsFabricChassisEpEntry 20 }

cucsFabricChassisEpSlotId OBJECT-TYPE
    SYNTAX       CucsFabricPIoEpSlotId
    MAX-ACCESS   read-only
    STATUS       current
    DESCRIPTION
        "Cisco UCS fabric:ChassisEp:slotId managed object property"
    ::= { cucsFabricChassisEpEntry 21 }

cucsFabricChassisEpSwitchId OBJECT-TYPE
    SYNTAX       CucsNetworkSwitchId
    MAX-ACCESS   read-only
    STATUS       current
    DESCRIPTION
        "Cisco UCS fabric:ChassisEp:switchId managed object property"
    ::= { cucsFabricChassisEpEntry 22 }

cucsFabricChassisEpTransport OBJECT-TYPE
    SYNTAX       CucsNetworkTransport
    MAX-ACCESS   read-only
    STATUS       current
    DESCRIPTION
        "Cisco UCS fabric:ChassisEp:transport managed object property"
    ::= { cucsFabricChassisEpEntry 23 }

cucsFabricChassisEpType OBJECT-TYPE
    SYNTAX       CucsFabricComputeEpType
    MAX-ACCESS   read-only
    STATUS       current
    DESCRIPTION
        "Cisco UCS fabric:ChassisEp:type managed object property"
    ::= { cucsFabricChassisEpEntry 24 }

cucsFabricChassisEpVendor OBJECT-TYPE
    SYNTAX       SnmpAdminString
    MAX-ACCESS   read-only
    STATUS       current
    DESCRIPTION
        "Cisco UCS fabric:ChassisEp:vendor managed object property"
    ::= { cucsFabricChassisEpEntry 25 }

cucsFabricChassisEpPeerChassisId OBJECT-TYPE
    SYNTAX       Gauge32
    MAX-ACCESS   read-only
    STATUS       current
    DESCRIPTION
        "Cisco UCS fabric:ChassisEp:peerChassisId managed object property"
    ::= { cucsFabricChassisEpEntry 26 }

cucsFabricChassisEpFltAggr OBJECT-TYPE
    SYNTAX       Unsigned64
    MAX-ACCESS   read-only
    STATUS       current
    DESCRIPTION
        "Cisco UCS fabric:ChassisEp:fltAggr managed object property"
    ::= { cucsFabricChassisEpEntry 27 }

cucsFabricComputePhEpTable OBJECT-TYPE
    SYNTAX           SEQUENCE OF CucsFabricComputePhEpEntry
    MAX-ACCESS       not-accessible
    STATUS           current
    DESCRIPTION
        "Cisco UCS fabric:ComputePhEp managed object table"
    ::= { cucsFabricObjects 2 }

cucsFabricComputePhEpEntry OBJECT-TYPE
    SYNTAX           CucsFabricComputePhEpEntry
    MAX-ACCESS       not-accessible
    STATUS           current
    DESCRIPTION
        "Entry for the cucsFabricComputePhEpTable table."
    INDEX { cucsFabricComputePhEpInstanceId }
    ::= { cucsFabricComputePhEpTable 1 }

CucsFabricComputePhEpEntry ::= SEQUENCE {
    cucsFabricComputePhEpInstanceId                                  CucsManagedObjectId,
    cucsFabricComputePhEpDn                                          CucsManagedObjectDn,
    cucsFabricComputePhEpRn                                          SnmpAdminString,
    cucsFabricComputePhEpAdminState                                  CucsFabricInternalEpAdminState,
    cucsFabricComputePhEpChassisId                                   Gauge32,
    cucsFabricComputePhEpEpDn                                        SnmpAdminString,
    cucsFabricComputePhEpEqType                                      CucsEquipmentFabricEpType,
    cucsFabricComputePhEpIfRole                                      CucsFabricComputeEpIfRole,
    cucsFabricComputePhEpIfType                                      CucsFabricPIoEpIfType,
    cucsFabricComputePhEpLc                                          CucsFabricBladeLifeCycle,
    cucsFabricComputePhEpLicGP                                       Unsigned64,
    cucsFabricComputePhEpLicState                                    CucsLicenseState,
    cucsFabricComputePhEpLocale                                      CucsFabricInternalEpLocale,
    cucsFabricComputePhEpModel                                       SnmpAdminString,
    cucsFabricComputePhEpName                                        SnmpAdminString,
    cucsFabricComputePhEpPeerDn                                      SnmpAdminString,
    cucsFabricComputePhEpPeerPortId                                  Gauge32,
    cucsFabricComputePhEpPeerSlotId                                  Gauge32,
    cucsFabricComputePhEpPortId                                      CucsFabricPIoEpPortId,
    cucsFabricComputePhEpProfileDn                                   SnmpAdminString,
    cucsFabricComputePhEpRevision                                    SnmpAdminString,
    cucsFabricComputePhEpSerial                                      SnmpAdminString,
    cucsFabricComputePhEpSlotId                                      CucsFabricPIoEpSlotId,
    cucsFabricComputePhEpSwitchId                                    CucsNetworkSwitchId,
    cucsFabricComputePhEpTransport                                   CucsNetworkTransport,
    cucsFabricComputePhEpType                                        CucsFabricComputeEpType,
    cucsFabricComputePhEpVendor                                      SnmpAdminString,
    cucsFabricComputePhEpPeerChassisId                               Gauge32,
    cucsFabricComputePhEpCheckpointTrigTs                            Unsigned64,
    cucsFabricComputePhEpDeepCheckpointTrigTs                        Unsigned64,
    cucsFabricComputePhEpDiscTrigTs                                  Unsigned64,
    cucsFabricComputePhEpFltAggr                                     Unsigned64
}

cucsFabricComputePhEpInstanceId OBJECT-TYPE
    SYNTAX       CucsManagedObjectId
    MAX-ACCESS   not-accessible
    STATUS       current
    DESCRIPTION
        "Instance identifier of the managed object."
    ::= { cucsFabricComputePhEpEntry 1 }

cucsFabricComputePhEpDn OBJECT-TYPE
    SYNTAX       CucsManagedObjectDn
    MAX-ACCESS   read-only
    STATUS       current
    DESCRIPTION
        "Cisco UCS fabric:ComputePhEp:dn managed object property"
    ::= { cucsFabricComputePhEpEntry 2 }

cucsFabricComputePhEpRn OBJECT-TYPE
    SYNTAX       SnmpAdminString
    MAX-ACCESS   read-only
    STATUS       current
    DESCRIPTION
        "Cisco UCS fabric:ComputePhEp:rn managed object property"
    ::= { cucsFabricComputePhEpEntry 3 }

cucsFabricComputePhEpAdminState OBJECT-TYPE
    SYNTAX       CucsFabricInternalEpAdminState
    MAX-ACCESS   read-only
    STATUS       current
    DESCRIPTION
        "Cisco UCS fabric:ComputePhEp:adminState managed object property"
    ::= { cucsFabricComputePhEpEntry 4 }

cucsFabricComputePhEpChassisId OBJECT-TYPE
    SYNTAX       Gauge32
    MAX-ACCESS   read-only
    STATUS       current
    DESCRIPTION
        "Cisco UCS fabric:ComputePhEp:chassisId managed object property"
    ::= { cucsFabricComputePhEpEntry 5 }

cucsFabricComputePhEpEpDn OBJECT-TYPE
    SYNTAX       SnmpAdminString
    MAX-ACCESS   read-only
    STATUS       current
    DESCRIPTION
        "Cisco UCS fabric:ComputePhEp:epDn managed object property"
    ::= { cucsFabricComputePhEpEntry 6 }

cucsFabricComputePhEpEqType OBJECT-TYPE
    SYNTAX       CucsEquipmentFabricEpType
    MAX-ACCESS   read-only
    STATUS       current
    DESCRIPTION
        "Cisco UCS fabric:ComputePhEp:eqType managed object property"
    ::= { cucsFabricComputePhEpEntry 7 }

cucsFabricComputePhEpIfRole OBJECT-TYPE
    SYNTAX       CucsFabricComputeEpIfRole
    MAX-ACCESS   read-only
    STATUS       current
    DESCRIPTION
        "Cisco UCS fabric:ComputePhEp:ifRole managed object property"
    ::= { cucsFabricComputePhEpEntry 8 }

cucsFabricComputePhEpIfType OBJECT-TYPE
    SYNTAX       CucsFabricPIoEpIfType
    MAX-ACCESS   read-only
    STATUS       current
    DESCRIPTION
        "Cisco UCS fabric:ComputePhEp:ifType managed object property"
    ::= { cucsFabricComputePhEpEntry 9 }

cucsFabricComputePhEpLc OBJECT-TYPE
    SYNTAX       CucsFabricBladeLifeCycle
    MAX-ACCESS   read-only
    STATUS       current
    DESCRIPTION
        "Cisco UCS fabric:ComputePhEp:lc managed object property"
    ::= { cucsFabricComputePhEpEntry 10 }

cucsFabricComputePhEpLicGP OBJECT-TYPE
    SYNTAX       Unsigned64
    MAX-ACCESS   read-only
    STATUS       current
    DESCRIPTION
        "Cisco UCS fabric:ComputePhEp:licGP managed object property"
    ::= { cucsFabricComputePhEpEntry 11 }

cucsFabricComputePhEpLicState OBJECT-TYPE
    SYNTAX       CucsLicenseState
    MAX-ACCESS   read-only
    STATUS       current
    DESCRIPTION
        "Cisco UCS fabric:ComputePhEp:licState managed object property"
    ::= { cucsFabricComputePhEpEntry 12 }

cucsFabricComputePhEpLocale OBJECT-TYPE
    SYNTAX       CucsFabricInternalEpLocale
    MAX-ACCESS   read-only
    STATUS       current
    DESCRIPTION
        "Cisco UCS fabric:ComputePhEp:locale managed object property"
    ::= { cucsFabricComputePhEpEntry 13 }

cucsFabricComputePhEpModel OBJECT-TYPE
    SYNTAX       SnmpAdminString
    MAX-ACCESS   read-only
    STATUS       current
    DESCRIPTION
        "Cisco UCS fabric:ComputePhEp:model managed object property"
    ::= { cucsFabricComputePhEpEntry 14 }

cucsFabricComputePhEpName OBJECT-TYPE
    SYNTAX       SnmpAdminString
    MAX-ACCESS   read-only
    STATUS       current
    DESCRIPTION
        "Cisco UCS fabric:ComputePhEp:name managed object property"
    ::= { cucsFabricComputePhEpEntry 15 }

cucsFabricComputePhEpPeerDn OBJECT-TYPE
    SYNTAX       SnmpAdminString
    MAX-ACCESS   read-only
    STATUS       current
    DESCRIPTION
        "Cisco UCS fabric:ComputePhEp:peerDn managed object property"
    ::= { cucsFabricComputePhEpEntry 16 }

cucsFabricComputePhEpPeerPortId OBJECT-TYPE
    SYNTAX       Gauge32
    MAX-ACCESS   read-only
    STATUS       current
    DESCRIPTION
        "Cisco UCS fabric:ComputePhEp:peerPortId managed object property"
    ::= { cucsFabricComputePhEpEntry 17 }

cucsFabricComputePhEpPeerSlotId OBJECT-TYPE
    SYNTAX       Gauge32
    MAX-ACCESS   read-only
    STATUS       current
    DESCRIPTION
        "Cisco UCS fabric:ComputePhEp:peerSlotId managed object property"
    ::= { cucsFabricComputePhEpEntry 18 }

cucsFabricComputePhEpPortId OBJECT-TYPE
    SYNTAX       CucsFabricPIoEpPortId
    MAX-ACCESS   read-only
    STATUS       current
    DESCRIPTION
        "Cisco UCS fabric:ComputePhEp:portId managed object property"
    ::= { cucsFabricComputePhEpEntry 19 }

cucsFabricComputePhEpProfileDn OBJECT-TYPE
    SYNTAX       SnmpAdminString
    MAX-ACCESS   read-only
    STATUS       current
    DESCRIPTION
        "Cisco UCS fabric:ComputePhEp:profileDn managed object property"
    ::= { cucsFabricComputePhEpEntry 20 }

cucsFabricComputePhEpRevision OBJECT-TYPE
    SYNTAX       SnmpAdminString
    MAX-ACCESS   read-only
    STATUS       current
    DESCRIPTION
        "Cisco UCS fabric:ComputePhEp:revision managed object property"
    ::= { cucsFabricComputePhEpEntry 21 }

cucsFabricComputePhEpSerial OBJECT-TYPE
    SYNTAX       SnmpAdminString
    MAX-ACCESS   read-only
    STATUS       current
    DESCRIPTION
        "Cisco UCS fabric:ComputePhEp:serial managed object property"
    ::= { cucsFabricComputePhEpEntry 22 }

cucsFabricComputePhEpSlotId OBJECT-TYPE
    SYNTAX       CucsFabricPIoEpSlotId
    MAX-ACCESS   read-only
    STATUS       current
    DESCRIPTION
        "Cisco UCS fabric:ComputePhEp:slotId managed object property"
    ::= { cucsFabricComputePhEpEntry 23 }

cucsFabricComputePhEpSwitchId OBJECT-TYPE
    SYNTAX       CucsNetworkSwitchId
    MAX-ACCESS   read-only
    STATUS       current
    DESCRIPTION
        "Cisco UCS fabric:ComputePhEp:switchId managed object property"
    ::= { cucsFabricComputePhEpEntry 24 }

cucsFabricComputePhEpTransport OBJECT-TYPE
    SYNTAX       CucsNetworkTransport
    MAX-ACCESS   read-only
    STATUS       current
    DESCRIPTION
        "Cisco UCS fabric:ComputePhEp:transport managed object property"
    ::= { cucsFabricComputePhEpEntry 25 }

cucsFabricComputePhEpType OBJECT-TYPE
    SYNTAX       CucsFabricComputeEpType
    MAX-ACCESS   read-only
    STATUS       current
    DESCRIPTION
        "Cisco UCS fabric:ComputePhEp:type managed object property"
    ::= { cucsFabricComputePhEpEntry 26 }

cucsFabricComputePhEpVendor OBJECT-TYPE
    SYNTAX       SnmpAdminString
    MAX-ACCESS   read-only
    STATUS       current
    DESCRIPTION
        "Cisco UCS fabric:ComputePhEp:vendor managed object property"
    ::= { cucsFabricComputePhEpEntry 27 }

cucsFabricComputePhEpPeerChassisId OBJECT-TYPE
    SYNTAX       Gauge32
    MAX-ACCESS   read-only
    STATUS       current
    DESCRIPTION
        "Cisco UCS fabric:ComputePhEp:peerChassisId managed
        object property"
    ::= { cucsFabricComputePhEpEntry 28 }

cucsFabricComputePhEpCheckpointTrigTs OBJECT-TYPE
    SYNTAX       Unsigned64
    MAX-ACCESS   read-only
    STATUS       current
    DESCRIPTION
        "Cisco UCS fabric:ComputePhEp:checkpointTrigTs
        managed object property"
    ::= { cucsFabricComputePhEpEntry 29 }

cucsFabricComputePhEpDeepCheckpointTrigTs OBJECT-TYPE
    SYNTAX       Unsigned64
    MAX-ACCESS   read-only
    STATUS       current
    DESCRIPTION
        "Cisco UCS fabric:ComputePhEp:deepCheckpointTrigTs
        managed object property"
    ::= { cucsFabricComputePhEpEntry 30 }

cucsFabricComputePhEpDiscTrigTs OBJECT-TYPE
    SYNTAX       Unsigned64
    MAX-ACCESS   read-only
    STATUS       current
    DESCRIPTION
        "Cisco UCS fabric:ComputePhEp:discTrigTs managed object property"
    ::= { cucsFabricComputePhEpEntry 31 }

cucsFabricComputePhEpFltAggr OBJECT-TYPE
    SYNTAX       Unsigned64
    MAX-ACCESS   read-only
    STATUS       current
    DESCRIPTION
        "Cisco UCS fabric:ComputePhEp:fltAggr managed object property"
    ::= { cucsFabricComputePhEpEntry 32 }

cucsFabricComputeSlotEpTable OBJECT-TYPE
    SYNTAX           SEQUENCE OF CucsFabricComputeSlotEpEntry
    MAX-ACCESS       not-accessible
    STATUS           current
    DESCRIPTION
        "Cisco UCS fabric:ComputeSlotEp managed object table"
    ::= { cucsFabricObjects 3 }

cucsFabricComputeSlotEpEntry OBJECT-TYPE
    SYNTAX           CucsFabricComputeSlotEpEntry
    MAX-ACCESS       not-accessible
    STATUS           current
    DESCRIPTION
        "Entry for the cucsFabricComputeSlotEpTable table."
    INDEX { cucsFabricComputeSlotEpInstanceId }
    ::= { cucsFabricComputeSlotEpTable 1 }

CucsFabricComputeSlotEpEntry ::= SEQUENCE {
    cucsFabricComputeSlotEpInstanceId                                CucsManagedObjectId,
    cucsFabricComputeSlotEpDn                                        CucsManagedObjectDn,
    cucsFabricComputeSlotEpRn                                        SnmpAdminString,
    cucsFabricComputeSlotEpAdminState                                CucsFabricSlotAdminState,
    cucsFabricComputeSlotEpChassisId                                 Gauge32,
    cucsFabricComputeSlotEpConnPath                                  CucsEquipmentConnectionStatus,
    cucsFabricComputeSlotEpConnStatus                                CucsEquipmentConnectionStatus,
    cucsFabricComputeSlotEpDiscovery                                 CucsComputeDiscovery,
    cucsFabricComputeSlotEpEpDn                                      SnmpAdminString,
    cucsFabricComputeSlotEpFltAggr                                   Unsigned64,
    cucsFabricComputeSlotEpFsmDescr                                  SnmpAdminString,
    cucsFabricComputeSlotEpFsmPrev                                   SnmpAdminString,
    cucsFabricComputeSlotEpFsmProgr                                  Gauge32,
    cucsFabricComputeSlotEpFsmRmtInvErrCode                          Gauge32,
    cucsFabricComputeSlotEpFsmRmtInvErrDescr                         SnmpAdminString,
    cucsFabricComputeSlotEpFsmRmtInvRslt                             CucsConditionRemoteInvRslt,
    cucsFabricComputeSlotEpFsmStageDescr                             SnmpAdminString,
    cucsFabricComputeSlotEpFsmStamp                                  DateAndTime,
    cucsFabricComputeSlotEpFsmStatus                                 SnmpAdminString,
    cucsFabricComputeSlotEpFsmTry                                    Gauge32,
    cucsFabricComputeSlotEpIfRole                                    CucsFabricComputeEpIfRole,
    cucsFabricComputeSlotEpIfType                                    CucsFabricPIoEpIfType,
    cucsFabricComputeSlotEpLcTs                                      DateAndTime,
    cucsFabricComputeSlotEpLicGP                                     Unsigned64,
    cucsFabricComputeSlotEpLicState                                  CucsLicenseState,
    cucsFabricComputeSlotEpLocale                                    CucsFabricInternalEpLocale,
    cucsFabricComputeSlotEpManagingInst                              CucsNetworkSwitchId,
    cucsFabricComputeSlotEpModel                                     SnmpAdminString,
    cucsFabricComputeSlotEpName                                      SnmpAdminString,
    cucsFabricComputeSlotEpPeerDn                                    SnmpAdminString,
    cucsFabricComputeSlotEpPeerPortId                                Gauge32,
    cucsFabricComputeSlotEpPeerSlotId                                Gauge32,
    cucsFabricComputeSlotEpPortId                                    CucsFabricPIoEpPortId,
    cucsFabricComputeSlotEpPresence                                  CucsEquipmentSlotStatus,
    cucsFabricComputeSlotEpRevision                                  SnmpAdminString,
    cucsFabricComputeSlotEpSerial                                    SnmpAdminString,
    cucsFabricComputeSlotEpSlotId                                    CucsFabricComputeSlotEpSlotId,
    cucsFabricComputeSlotEpSwitchId                                  CucsNetworkSwitchId,
    cucsFabricComputeSlotEpTransport                                 CucsNetworkTransport,
    cucsFabricComputeSlotEpType                                      CucsFabricComputeEpType,
    cucsFabricComputeSlotEpVendor                                    SnmpAdminString,
    cucsFabricComputeSlotEpPeerChassisId                             Gauge32,
    cucsFabricComputeSlotEpFruIdentTrigTs                            Unsigned64
}

cucsFabricComputeSlotEpInstanceId OBJECT-TYPE
    SYNTAX       CucsManagedObjectId
    MAX-ACCESS   not-accessible
    STATUS       current
    DESCRIPTION
        "Instance identifier of the managed object."
    ::= { cucsFabricComputeSlotEpEntry 1 }

cucsFabricComputeSlotEpDn OBJECT-TYPE
    SYNTAX       CucsManagedObjectDn
    MAX-ACCESS   read-only
    STATUS       current
    DESCRIPTION
        "Cisco UCS fabric:ComputeSlotEp:dn managed object property"
    ::= { cucsFabricComputeSlotEpEntry 2 }

cucsFabricComputeSlotEpRn OBJECT-TYPE
    SYNTAX       SnmpAdminString
    MAX-ACCESS   read-only
    STATUS       current
    DESCRIPTION
        "Cisco UCS fabric:ComputeSlotEp:rn managed object property"
    ::= { cucsFabricComputeSlotEpEntry 3 }

cucsFabricComputeSlotEpAdminState OBJECT-TYPE
    SYNTAX       CucsFabricSlotAdminState
    MAX-ACCESS   read-only
    STATUS       current
    DESCRIPTION
        "Cisco UCS fabric:ComputeSlotEp:adminState managed
        object property"
    ::= { cucsFabricComputeSlotEpEntry 4 }

cucsFabricComputeSlotEpChassisId OBJECT-TYPE
    SYNTAX       Gauge32
    MAX-ACCESS   read-only
    STATUS       current
    DESCRIPTION
        "Cisco UCS fabric:ComputeSlotEp:chassisId managed object property"
    ::= { cucsFabricComputeSlotEpEntry 5 }

cucsFabricComputeSlotEpConnPath OBJECT-TYPE
    SYNTAX       CucsEquipmentConnectionStatus
    MAX-ACCESS   read-only
    STATUS       current
    DESCRIPTION
        "Cisco UCS fabric:ComputeSlotEp:connPath managed object property"
    ::= { cucsFabricComputeSlotEpEntry 6 }

cucsFabricComputeSlotEpConnStatus OBJECT-TYPE
    SYNTAX       CucsEquipmentConnectionStatus
    MAX-ACCESS   read-only
    STATUS       current
    DESCRIPTION
        "Cisco UCS fabric:ComputeSlotEp:connStatus managed
        object property"
    ::= { cucsFabricComputeSlotEpEntry 7 }

cucsFabricComputeSlotEpDiscovery OBJECT-TYPE
    SYNTAX       CucsComputeDiscovery
    MAX-ACCESS   read-only
    STATUS       current
    DESCRIPTION
        "Cisco UCS fabric:ComputeSlotEp:discovery managed object property"
    ::= { cucsFabricComputeSlotEpEntry 8 }

cucsFabricComputeSlotEpEpDn OBJECT-TYPE
    SYNTAX       SnmpAdminString
    MAX-ACCESS   read-only
    STATUS       current
    DESCRIPTION
        "Cisco UCS fabric:ComputeSlotEp:epDn managed object property"
    ::= { cucsFabricComputeSlotEpEntry 9 }

cucsFabricComputeSlotEpFltAggr OBJECT-TYPE
    SYNTAX       Unsigned64
    MAX-ACCESS   read-only
    STATUS       current
    DESCRIPTION
        "Cisco UCS fabric:ComputeSlotEp:fltAggr managed object property"
    ::= { cucsFabricComputeSlotEpEntry 10 }

cucsFabricComputeSlotEpFsmDescr OBJECT-TYPE
    SYNTAX       SnmpAdminString
    MAX-ACCESS   read-only
    STATUS       current
    DESCRIPTION
        "Cisco UCS fabric:ComputeSlotEp:fsmDescr managed object property"
    ::= { cucsFabricComputeSlotEpEntry 11 }

cucsFabricComputeSlotEpFsmPrev OBJECT-TYPE
    SYNTAX       SnmpAdminString
    MAX-ACCESS   read-only
    STATUS       current
    DESCRIPTION
        "Cisco UCS fabric:ComputeSlotEp:fsmPrev managed object property"
    ::= { cucsFabricComputeSlotEpEntry 12 }

cucsFabricComputeSlotEpFsmProgr OBJECT-TYPE
    SYNTAX       Gauge32
    MAX-ACCESS   read-only
    STATUS       current
    DESCRIPTION
        "Cisco UCS fabric:ComputeSlotEp:fsmProgr managed object property"
    ::= { cucsFabricComputeSlotEpEntry 13 }

cucsFabricComputeSlotEpFsmRmtInvErrCode OBJECT-TYPE
    SYNTAX       Gauge32
    MAX-ACCESS   read-only
    STATUS       current
    DESCRIPTION
        "Cisco UCS fabric:ComputeSlotEp:fsmRmtInvErrCode
        managed object property"
    ::= { cucsFabricComputeSlotEpEntry 14 }

cucsFabricComputeSlotEpFsmRmtInvErrDescr OBJECT-TYPE
    SYNTAX       SnmpAdminString
    MAX-ACCESS   read-only
    STATUS       current
    DESCRIPTION
        "Cisco UCS fabric:ComputeSlotEp:fsmRmtInvErrDescr
        managed object property"
    ::= { cucsFabricComputeSlotEpEntry 15 }

cucsFabricComputeSlotEpFsmRmtInvRslt OBJECT-TYPE
    SYNTAX       CucsConditionRemoteInvRslt
    MAX-ACCESS   read-only
    STATUS       current
    DESCRIPTION
        "Cisco UCS fabric:ComputeSlotEp:fsmRmtInvRslt managed
        object property"
    ::= { cucsFabricComputeSlotEpEntry 16 }

cucsFabricComputeSlotEpFsmStageDescr OBJECT-TYPE
    SYNTAX       SnmpAdminString
    MAX-ACCESS   read-only
    STATUS       current
    DESCRIPTION
        "Cisco UCS fabric:ComputeSlotEp:fsmStageDescr managed
        object property"
    ::= { cucsFabricComputeSlotEpEntry 17 }

cucsFabricComputeSlotEpFsmStamp OBJECT-TYPE
    SYNTAX       DateAndTime
    MAX-ACCESS   read-only
    STATUS       current
    DESCRIPTION
        "Cisco UCS fabric:ComputeSlotEp:fsmStamp managed object property"
    ::= { cucsFabricComputeSlotEpEntry 18 }

cucsFabricComputeSlotEpFsmStatus OBJECT-TYPE
    SYNTAX       SnmpAdminString
    MAX-ACCESS   read-only
    STATUS       current
    DESCRIPTION
        "Cisco UCS fabric:ComputeSlotEp:fsmStatus managed object property"
    ::= { cucsFabricComputeSlotEpEntry 19 }

cucsFabricComputeSlotEpFsmTry OBJECT-TYPE
    SYNTAX       Gauge32
    MAX-ACCESS   read-only
    STATUS       current
    DESCRIPTION
        "Cisco UCS fabric:ComputeSlotEp:fsmTry managed object property"
    ::= { cucsFabricComputeSlotEpEntry 20 }

cucsFabricComputeSlotEpIfRole OBJECT-TYPE
    SYNTAX       CucsFabricComputeEpIfRole
    MAX-ACCESS   read-only
    STATUS       current
    DESCRIPTION
        "Cisco UCS fabric:ComputeSlotEp:ifRole managed object property"
    ::= { cucsFabricComputeSlotEpEntry 21 }

cucsFabricComputeSlotEpIfType OBJECT-TYPE
    SYNTAX       CucsFabricPIoEpIfType
    MAX-ACCESS   read-only
    STATUS       current
    DESCRIPTION
        "Cisco UCS fabric:ComputeSlotEp:ifType managed object property"
    ::= { cucsFabricComputeSlotEpEntry 22 }

cucsFabricComputeSlotEpLcTs OBJECT-TYPE
    SYNTAX       DateAndTime
    MAX-ACCESS   read-only
    STATUS       current
    DESCRIPTION
        "Cisco UCS fabric:ComputeSlotEp:lcTs managed object property"
    ::= { cucsFabricComputeSlotEpEntry 23 }

cucsFabricComputeSlotEpLicGP OBJECT-TYPE
    SYNTAX       Unsigned64
    MAX-ACCESS   read-only
    STATUS       current
    DESCRIPTION
        "Cisco UCS fabric:ComputeSlotEp:licGP managed object property"
    ::= { cucsFabricComputeSlotEpEntry 24 }

cucsFabricComputeSlotEpLicState OBJECT-TYPE
    SYNTAX       CucsLicenseState
    MAX-ACCESS   read-only
    STATUS       current
    DESCRIPTION
        "Cisco UCS fabric:ComputeSlotEp:licState managed object property"
    ::= { cucsFabricComputeSlotEpEntry 25 }

cucsFabricComputeSlotEpLocale OBJECT-TYPE
    SYNTAX       CucsFabricInternalEpLocale
    MAX-ACCESS   read-only
    STATUS       current
    DESCRIPTION
        "Cisco UCS fabric:ComputeSlotEp:locale managed object property"
    ::= { cucsFabricComputeSlotEpEntry 26 }

cucsFabricComputeSlotEpManagingInst OBJECT-TYPE
    SYNTAX       CucsNetworkSwitchId
    MAX-ACCESS   read-only
    STATUS       current
    DESCRIPTION
        "Cisco UCS fabric:ComputeSlotEp:managingInst managed
        object property"
    ::= { cucsFabricComputeSlotEpEntry 27 }

cucsFabricComputeSlotEpModel OBJECT-TYPE
    SYNTAX       SnmpAdminString
    MAX-ACCESS   read-only
    STATUS       current
    DESCRIPTION
        "Cisco UCS fabric:ComputeSlotEp:model managed object property"
    ::= { cucsFabricComputeSlotEpEntry 28 }

cucsFabricComputeSlotEpName OBJECT-TYPE
    SYNTAX       SnmpAdminString
    MAX-ACCESS   read-only
    STATUS       current
    DESCRIPTION
        "Cisco UCS fabric:ComputeSlotEp:name managed object property"
    ::= { cucsFabricComputeSlotEpEntry 29 }

cucsFabricComputeSlotEpPeerDn OBJECT-TYPE
    SYNTAX       SnmpAdminString
    MAX-ACCESS   read-only
    STATUS       current
    DESCRIPTION
        "Cisco UCS fabric:ComputeSlotEp:peerDn managed object property"
    ::= { cucsFabricComputeSlotEpEntry 30 }

cucsFabricComputeSlotEpPeerPortId OBJECT-TYPE
    SYNTAX       Gauge32
    MAX-ACCESS   read-only
    STATUS       current
    DESCRIPTION
        "Cisco UCS fabric:ComputeSlotEp:peerPortId managed
        object property"
    ::= { cucsFabricComputeSlotEpEntry 31 }

cucsFabricComputeSlotEpPeerSlotId OBJECT-TYPE
    SYNTAX       Gauge32
    MAX-ACCESS   read-only
    STATUS       current
    DESCRIPTION
        "Cisco UCS fabric:ComputeSlotEp:peerSlotId managed
        object property"
    ::= { cucsFabricComputeSlotEpEntry 32 }

cucsFabricComputeSlotEpPortId OBJECT-TYPE
    SYNTAX       CucsFabricPIoEpPortId
    MAX-ACCESS   read-only
    STATUS       current
    DESCRIPTION
        "Cisco UCS fabric:ComputeSlotEp:portId managed object property"
    ::= { cucsFabricComputeSlotEpEntry 33 }

cucsFabricComputeSlotEpPresence OBJECT-TYPE
    SYNTAX       CucsEquipmentSlotStatus
    MAX-ACCESS   read-only
    STATUS       current
    DESCRIPTION
        "Cisco UCS fabric:ComputeSlotEp:presence managed object property"
    ::= { cucsFabricComputeSlotEpEntry 34 }

cucsFabricComputeSlotEpRevision OBJECT-TYPE
    SYNTAX       SnmpAdminString
    MAX-ACCESS   read-only
    STATUS       current
    DESCRIPTION
        "Cisco UCS fabric:ComputeSlotEp:revision managed object property"
    ::= { cucsFabricComputeSlotEpEntry 35 }

cucsFabricComputeSlotEpSerial OBJECT-TYPE
    SYNTAX       SnmpAdminString
    MAX-ACCESS   read-only
    STATUS       current
    DESCRIPTION
        "Cisco UCS fabric:ComputeSlotEp:serial managed object property"
    ::= { cucsFabricComputeSlotEpEntry 36 }

cucsFabricComputeSlotEpSlotId OBJECT-TYPE
    SYNTAX       CucsFabricComputeSlotEpSlotId
    MAX-ACCESS   read-only
    STATUS       current
    DESCRIPTION
        "Cisco UCS fabric:ComputeSlotEp:slotId managed object property"
    ::= { cucsFabricComputeSlotEpEntry 37 }

cucsFabricComputeSlotEpSwitchId OBJECT-TYPE
    SYNTAX       CucsNetworkSwitchId
    MAX-ACCESS   read-only
    STATUS       current
    DESCRIPTION
        "Cisco UCS fabric:ComputeSlotEp:switchId managed object property"
    ::= { cucsFabricComputeSlotEpEntry 38 }

cucsFabricComputeSlotEpTransport OBJECT-TYPE
    SYNTAX       CucsNetworkTransport
    MAX-ACCESS   read-only
    STATUS       current
    DESCRIPTION
        "Cisco UCS fabric:ComputeSlotEp:transport managed object property"
    ::= { cucsFabricComputeSlotEpEntry 39 }

cucsFabricComputeSlotEpType OBJECT-TYPE
    SYNTAX       CucsFabricComputeEpType
    MAX-ACCESS   read-only
    STATUS       current
    DESCRIPTION
        "Cisco UCS fabric:ComputeSlotEp:type managed object property"
    ::= { cucsFabricComputeSlotEpEntry 40 }

cucsFabricComputeSlotEpVendor OBJECT-TYPE
    SYNTAX       SnmpAdminString
    MAX-ACCESS   read-only
    STATUS       current
    DESCRIPTION
        "Cisco UCS fabric:ComputeSlotEp:vendor managed object property"
    ::= { cucsFabricComputeSlotEpEntry 41 }

cucsFabricComputeSlotEpPeerChassisId OBJECT-TYPE
    SYNTAX       Gauge32
    MAX-ACCESS   read-only
    STATUS       current
    DESCRIPTION
        "Cisco UCS fabric:ComputeSlotEp:peerChassisId managed
        object property"
    ::= { cucsFabricComputeSlotEpEntry 42 }

cucsFabricComputeSlotEpFruIdentTrigTs OBJECT-TYPE
    SYNTAX       Unsigned64
    MAX-ACCESS   read-only
    STATUS       current
    DESCRIPTION
        "Cisco UCS fabric:ComputeSlotEp:fruIdentTrigTs
        managed object property"
    ::= { cucsFabricComputeSlotEpEntry 43 }

cucsFabricComputeSlotEpFsmTaskTable OBJECT-TYPE
    SYNTAX           SEQUENCE OF CucsFabricComputeSlotEpFsmTaskEntry
    MAX-ACCESS       not-accessible
    STATUS           current
    DESCRIPTION
        "Cisco UCS fabric:ComputeSlotEpFsmTask managed object table"
    ::= { cucsFabricObjects 4 }

cucsFabricComputeSlotEpFsmTaskEntry OBJECT-TYPE
    SYNTAX           CucsFabricComputeSlotEpFsmTaskEntry
    MAX-ACCESS       not-accessible
    STATUS           current
    DESCRIPTION
        "Entry for the cucsFabricComputeSlotEpFsmTaskTable table."
    INDEX { cucsFabricComputeSlotEpFsmTaskInstanceId }
    ::= { cucsFabricComputeSlotEpFsmTaskTable 1 }

CucsFabricComputeSlotEpFsmTaskEntry ::= SEQUENCE {
    cucsFabricComputeSlotEpFsmTaskInstanceId                         CucsManagedObjectId,
    cucsFabricComputeSlotEpFsmTaskDn                                 CucsManagedObjectDn,
    cucsFabricComputeSlotEpFsmTaskRn                                 SnmpAdminString,
    cucsFabricComputeSlotEpFsmTaskCompletion                         CucsFsmCompletion,
    cucsFabricComputeSlotEpFsmTaskFlags                              CucsFsmFlags,
    cucsFabricComputeSlotEpFsmTaskItem                               CucsFabricComputeSlotEpFsmTaskItem,
    cucsFabricComputeSlotEpFsmTaskSeqId                              Gauge32
}

cucsFabricComputeSlotEpFsmTaskInstanceId OBJECT-TYPE
    SYNTAX       CucsManagedObjectId
    MAX-ACCESS   not-accessible
    STATUS       current
    DESCRIPTION
        "Instance identifier of the managed object."
    ::= { cucsFabricComputeSlotEpFsmTaskEntry 1 }

cucsFabricComputeSlotEpFsmTaskDn OBJECT-TYPE
    SYNTAX       CucsManagedObjectDn
    MAX-ACCESS   read-only
    STATUS       current
    DESCRIPTION
        "Cisco UCS fabric:ComputeSlotEpFsmTask:dn managed object property"
    ::= { cucsFabricComputeSlotEpFsmTaskEntry 2 }

cucsFabricComputeSlotEpFsmTaskRn OBJECT-TYPE
    SYNTAX       SnmpAdminString
    MAX-ACCESS   read-only
    STATUS       current
    DESCRIPTION
        "Cisco UCS fabric:ComputeSlotEpFsmTask:rn managed object property"
    ::= { cucsFabricComputeSlotEpFsmTaskEntry 3 }

cucsFabricComputeSlotEpFsmTaskCompletion OBJECT-TYPE
    SYNTAX       CucsFsmCompletion
    MAX-ACCESS   read-only
    STATUS       current
    DESCRIPTION
        "Cisco UCS fabric:ComputeSlotEpFsmTask:completion
        managed object property"
    ::= { cucsFabricComputeSlotEpFsmTaskEntry 4 }

cucsFabricComputeSlotEpFsmTaskFlags OBJECT-TYPE
    SYNTAX       CucsFsmFlags
    MAX-ACCESS   read-only
    STATUS       current
    DESCRIPTION
        "Cisco UCS fabric:ComputeSlotEpFsmTask:flags managed
        object property"
    ::= { cucsFabricComputeSlotEpFsmTaskEntry 5 }

cucsFabricComputeSlotEpFsmTaskItem OBJECT-TYPE
    SYNTAX       CucsFabricComputeSlotEpFsmTaskItem
    MAX-ACCESS   read-only
    STATUS       current
    DESCRIPTION
        "Cisco UCS fabric:ComputeSlotEpFsmTask:item managed
        object property"
    ::= { cucsFabricComputeSlotEpFsmTaskEntry 6 }

cucsFabricComputeSlotEpFsmTaskSeqId OBJECT-TYPE
    SYNTAX       Gauge32
    MAX-ACCESS   read-only
    STATUS       current
    DESCRIPTION
        "Cisco UCS fabric:ComputeSlotEpFsmTask:seqId managed
        object property"
    ::= { cucsFabricComputeSlotEpFsmTaskEntry 7 }

cucsFabricDceSrvTable OBJECT-TYPE
    SYNTAX           SEQUENCE OF CucsFabricDceSrvEntry
    MAX-ACCESS       not-accessible
    STATUS           current
    DESCRIPTION
        "Cisco UCS fabric:DceSrv managed object table"
    ::= { cucsFabricObjects 5 }

cucsFabricDceSrvEntry OBJECT-TYPE
    SYNTAX           CucsFabricDceSrvEntry
    MAX-ACCESS       not-accessible
    STATUS           current
    DESCRIPTION
        "Entry for the cucsFabricDceSrvTable table."
    INDEX { cucsFabricDceSrvInstanceId }
    ::= { cucsFabricDceSrvTable 1 }

CucsFabricDceSrvEntry ::= SEQUENCE {
    cucsFabricDceSrvInstanceId                                       CucsManagedObjectId,
    cucsFabricDceSrvDn                                               CucsManagedObjectDn,
    cucsFabricDceSrvRn                                               SnmpAdminString,
    cucsFabricDceSrvId                                               CucsNetworkSwitchId,
    cucsFabricDceSrvLocale                                           CucsFabricInternalLocale,
    cucsFabricDceSrvName                                             SnmpAdminString,
    cucsFabricDceSrvTransport                                        CucsFabricInternalDceSrvTransport,
    cucsFabricDceSrvType                                             CucsFabricInternalDceSrvType
}

cucsFabricDceSrvInstanceId OBJECT-TYPE
    SYNTAX       CucsManagedObjectId
    MAX-ACCESS   not-accessible
    STATUS       current
    DESCRIPTION
        "Instance identifier of the managed object."
    ::= { cucsFabricDceSrvEntry 1 }

cucsFabricDceSrvDn OBJECT-TYPE
    SYNTAX       CucsManagedObjectDn
    MAX-ACCESS   read-only
    STATUS       current
    DESCRIPTION
        "Cisco UCS fabric:DceSrv:dn managed object property"
    ::= { cucsFabricDceSrvEntry 2 }

cucsFabricDceSrvRn OBJECT-TYPE
    SYNTAX       SnmpAdminString
    MAX-ACCESS   read-only
    STATUS       current
    DESCRIPTION
        "Cisco UCS fabric:DceSrv:rn managed object property"
    ::= { cucsFabricDceSrvEntry 3 }

cucsFabricDceSrvId OBJECT-TYPE
    SYNTAX       CucsNetworkSwitchId
    MAX-ACCESS   read-only
    STATUS       current
    DESCRIPTION
        "Cisco UCS fabric:DceSrv:id managed object property"
    ::= { cucsFabricDceSrvEntry 4 }

cucsFabricDceSrvLocale OBJECT-TYPE
    SYNTAX       CucsFabricInternalLocale
    MAX-ACCESS   read-only
    STATUS       current
    DESCRIPTION
        "Cisco UCS fabric:DceSrv:locale managed object property"
    ::= { cucsFabricDceSrvEntry 5 }

cucsFabricDceSrvName OBJECT-TYPE
    SYNTAX       SnmpAdminString
    MAX-ACCESS   read-only
    STATUS       current
    DESCRIPTION
        "Cisco UCS fabric:DceSrv:name managed object property"
    ::= { cucsFabricDceSrvEntry 6 }

cucsFabricDceSrvTransport OBJECT-TYPE
    SYNTAX       CucsFabricInternalDceSrvTransport
    MAX-ACCESS   read-only
    STATUS       current
    DESCRIPTION
        "Cisco UCS fabric:DceSrv:transport managed object property"
    ::= { cucsFabricDceSrvEntry 7 }

cucsFabricDceSrvType OBJECT-TYPE
    SYNTAX       CucsFabricInternalDceSrvType
    MAX-ACCESS   read-only
    STATUS       current
    DESCRIPTION
        "Cisco UCS fabric:DceSrv:type managed object property"
    ::= { cucsFabricDceSrvEntry 8 }

cucsFabricDceSwSrvTable OBJECT-TYPE
    SYNTAX           SEQUENCE OF CucsFabricDceSwSrvEntry
    MAX-ACCESS       not-accessible
    STATUS           current
    DESCRIPTION
        "Cisco UCS fabric:DceSwSrv managed object table"
    ::= { cucsFabricObjects 6 }

cucsFabricDceSwSrvEntry OBJECT-TYPE
    SYNTAX           CucsFabricDceSwSrvEntry
    MAX-ACCESS       not-accessible
    STATUS           current
    DESCRIPTION
        "Entry for the cucsFabricDceSwSrvTable table."
    INDEX { cucsFabricDceSwSrvInstanceId }
    ::= { cucsFabricDceSwSrvTable 1 }

CucsFabricDceSwSrvEntry ::= SEQUENCE {
    cucsFabricDceSwSrvInstanceId                                     CucsManagedObjectId,
    cucsFabricDceSwSrvDn                                             CucsManagedObjectDn,
    cucsFabricDceSwSrvRn                                             SnmpAdminString,
    cucsFabricDceSwSrvId                                             CucsNetworkSwitchId,
    cucsFabricDceSwSrvLocale                                         CucsFabricInternalLocale,
    cucsFabricDceSwSrvName                                           SnmpAdminString,
    cucsFabricDceSwSrvTransport                                      CucsFabricInternalDceSrvTransport,
    cucsFabricDceSwSrvType                                           CucsFabricInternalDceSrvType
}

cucsFabricDceSwSrvInstanceId OBJECT-TYPE
    SYNTAX       CucsManagedObjectId
    MAX-ACCESS   not-accessible
    STATUS       current
    DESCRIPTION
        "Instance identifier of the managed object."
    ::= { cucsFabricDceSwSrvEntry 1 }

cucsFabricDceSwSrvDn OBJECT-TYPE
    SYNTAX       CucsManagedObjectDn
    MAX-ACCESS   read-only
    STATUS       current
    DESCRIPTION
        "Cisco UCS fabric:DceSwSrv:dn managed object property"
    ::= { cucsFabricDceSwSrvEntry 2 }

cucsFabricDceSwSrvRn OBJECT-TYPE
    SYNTAX       SnmpAdminString
    MAX-ACCESS   read-only
    STATUS       current
    DESCRIPTION
        "Cisco UCS fabric:DceSwSrv:rn managed object property"
    ::= { cucsFabricDceSwSrvEntry 3 }

cucsFabricDceSwSrvId OBJECT-TYPE
    SYNTAX       CucsNetworkSwitchId
    MAX-ACCESS   read-only
    STATUS       current
    DESCRIPTION
        "Cisco UCS fabric:DceSwSrv:id managed object property"
    ::= { cucsFabricDceSwSrvEntry 4 }

cucsFabricDceSwSrvLocale OBJECT-TYPE
    SYNTAX       CucsFabricInternalLocale
    MAX-ACCESS   read-only
    STATUS       current
    DESCRIPTION
        "Cisco UCS fabric:DceSwSrv:locale managed object property"
    ::= { cucsFabricDceSwSrvEntry 5 }

cucsFabricDceSwSrvName OBJECT-TYPE
    SYNTAX       SnmpAdminString
    MAX-ACCESS   read-only
    STATUS       current
    DESCRIPTION
        "Cisco UCS fabric:DceSwSrv:name managed object property"
    ::= { cucsFabricDceSwSrvEntry 6 }

cucsFabricDceSwSrvTransport OBJECT-TYPE
    SYNTAX       CucsFabricInternalDceSrvTransport
    MAX-ACCESS   read-only
    STATUS       current
    DESCRIPTION
        "Cisco UCS fabric:DceSwSrv:transport managed object property"
    ::= { cucsFabricDceSwSrvEntry 7 }

cucsFabricDceSwSrvType OBJECT-TYPE
    SYNTAX       CucsFabricInternalDceSrvType
    MAX-ACCESS   read-only
    STATUS       current
    DESCRIPTION
        "Cisco UCS fabric:DceSwSrv:type managed object property"
    ::= { cucsFabricDceSwSrvEntry 8 }

cucsFabricDceSwSrvEpTable OBJECT-TYPE
    SYNTAX           SEQUENCE OF CucsFabricDceSwSrvEpEntry
    MAX-ACCESS       not-accessible
    STATUS           current
    DESCRIPTION
        "Cisco UCS fabric:DceSwSrvEp managed object table"
    ::= { cucsFabricObjects 7 }

cucsFabricDceSwSrvEpEntry OBJECT-TYPE
    SYNTAX           CucsFabricDceSwSrvEpEntry
    MAX-ACCESS       not-accessible
    STATUS           current
    DESCRIPTION
        "Entry for the cucsFabricDceSwSrvEpTable table."
    INDEX { cucsFabricDceSwSrvEpInstanceId }
    ::= { cucsFabricDceSwSrvEpTable 1 }

CucsFabricDceSwSrvEpEntry ::= SEQUENCE {
    cucsFabricDceSwSrvEpInstanceId                                   CucsManagedObjectId,
    cucsFabricDceSwSrvEpDn                                           CucsManagedObjectDn,
    cucsFabricDceSwSrvEpRn                                           SnmpAdminString,
    cucsFabricDceSwSrvEpAdminState                                   CucsFabricInternalEpAdminState,
    cucsFabricDceSwSrvEpChassisId                                    Gauge32,
    cucsFabricDceSwSrvEpEpDn                                         SnmpAdminString,
    cucsFabricDceSwSrvEpIfRole                                       CucsFabricSwSrvEpIfRole,
    cucsFabricDceSwSrvEpIfType                                       CucsFabricPIoEpIfType,
    cucsFabricDceSwSrvEpLicGP                                        Unsigned64,
    cucsFabricDceSwSrvEpLicState                                     CucsLicenseState,
    cucsFabricDceSwSrvEpLocale                                       CucsFabricInternalEpLocale,
    cucsFabricDceSwSrvEpName                                         SnmpAdminString,
    cucsFabricDceSwSrvEpPeerDn                                       SnmpAdminString,
    cucsFabricDceSwSrvEpPeerPortId                                   Gauge32,
    cucsFabricDceSwSrvEpPeerSlotId                                   Gauge32,
    cucsFabricDceSwSrvEpPortId                                       CucsFabricDceSwSrvEpPortId,
    cucsFabricDceSwSrvEpSlotId                                       CucsFabricDceSwSrvEpSlotId,
    cucsFabricDceSwSrvEpSwitchId                                     CucsNetworkSwitchId,
    cucsFabricDceSwSrvEpTransport                                    CucsFabricADceSwSrvEpTransport,
    cucsFabricDceSwSrvEpType                                         CucsFabricSwSrvEpType,
    cucsFabricDceSwSrvEpUsrLbl                                       SnmpAdminString,
    cucsFabricDceSwSrvEpPeerChassisId                                Gauge32,
    cucsFabricDceSwSrvEpFltAggr                                      Unsigned64
}

cucsFabricDceSwSrvEpInstanceId OBJECT-TYPE
    SYNTAX       CucsManagedObjectId
    MAX-ACCESS   not-accessible
    STATUS       current
    DESCRIPTION
        "Instance identifier of the managed object."
    ::= { cucsFabricDceSwSrvEpEntry 1 }

cucsFabricDceSwSrvEpDn OBJECT-TYPE
    SYNTAX       CucsManagedObjectDn
    MAX-ACCESS   read-only
    STATUS       current
    DESCRIPTION
        "Cisco UCS fabric:DceSwSrvEp:dn managed object property"
    ::= { cucsFabricDceSwSrvEpEntry 2 }

cucsFabricDceSwSrvEpRn OBJECT-TYPE
    SYNTAX       SnmpAdminString
    MAX-ACCESS   read-only
    STATUS       current
    DESCRIPTION
        "Cisco UCS fabric:DceSwSrvEp:rn managed object property"
    ::= { cucsFabricDceSwSrvEpEntry 3 }

cucsFabricDceSwSrvEpAdminState OBJECT-TYPE
    SYNTAX       CucsFabricInternalEpAdminState
    MAX-ACCESS   read-only
    STATUS       current
    DESCRIPTION
        "Cisco UCS fabric:DceSwSrvEp:adminState managed object property"
    ::= { cucsFabricDceSwSrvEpEntry 4 }

cucsFabricDceSwSrvEpChassisId OBJECT-TYPE
    SYNTAX       Gauge32
    MAX-ACCESS   read-only
    STATUS       current
    DESCRIPTION
        "Cisco UCS fabric:DceSwSrvEp:chassisId managed object property"
    ::= { cucsFabricDceSwSrvEpEntry 5 }

cucsFabricDceSwSrvEpEpDn OBJECT-TYPE
    SYNTAX       SnmpAdminString
    MAX-ACCESS   read-only
    STATUS       current
    DESCRIPTION
        "Cisco UCS fabric:DceSwSrvEp:epDn managed object property"
    ::= { cucsFabricDceSwSrvEpEntry 6 }

cucsFabricDceSwSrvEpIfRole OBJECT-TYPE
    SYNTAX       CucsFabricSwSrvEpIfRole
    MAX-ACCESS   read-only
    STATUS       current
    DESCRIPTION
        "Cisco UCS fabric:DceSwSrvEp:ifRole managed object property"
    ::= { cucsFabricDceSwSrvEpEntry 7 }

cucsFabricDceSwSrvEpIfType OBJECT-TYPE
    SYNTAX       CucsFabricPIoEpIfType
    MAX-ACCESS   read-only
    STATUS       current
    DESCRIPTION
        "Cisco UCS fabric:DceSwSrvEp:ifType managed object property"
    ::= { cucsFabricDceSwSrvEpEntry 8 }

cucsFabricDceSwSrvEpLicGP OBJECT-TYPE
    SYNTAX       Unsigned64
    MAX-ACCESS   read-only
    STATUS       current
    DESCRIPTION
        "Cisco UCS fabric:DceSwSrvEp:licGP managed object property"
    ::= { cucsFabricDceSwSrvEpEntry 9 }

cucsFabricDceSwSrvEpLicState OBJECT-TYPE
    SYNTAX       CucsLicenseState
    MAX-ACCESS   read-only
    STATUS       current
    DESCRIPTION
        "Cisco UCS fabric:DceSwSrvEp:licState managed object property"
    ::= { cucsFabricDceSwSrvEpEntry 10 }

cucsFabricDceSwSrvEpLocale OBJECT-TYPE
    SYNTAX       CucsFabricInternalEpLocale
    MAX-ACCESS   read-only
    STATUS       current
    DESCRIPTION
        "Cisco UCS fabric:DceSwSrvEp:locale managed object property"
    ::= { cucsFabricDceSwSrvEpEntry 11 }

cucsFabricDceSwSrvEpName OBJECT-TYPE
    SYNTAX       SnmpAdminString
    MAX-ACCESS   read-only
    STATUS       current
    DESCRIPTION
        "Cisco UCS fabric:DceSwSrvEp:name managed object property"
    ::= { cucsFabricDceSwSrvEpEntry 12 }

cucsFabricDceSwSrvEpPeerDn OBJECT-TYPE
    SYNTAX       SnmpAdminString
    MAX-ACCESS   read-only
    STATUS       current
    DESCRIPTION
        "Cisco UCS fabric:DceSwSrvEp:peerDn managed object property"
    ::= { cucsFabricDceSwSrvEpEntry 13 }

cucsFabricDceSwSrvEpPeerPortId OBJECT-TYPE
    SYNTAX       Gauge32
    MAX-ACCESS   read-only
    STATUS       current
    DESCRIPTION
        "Cisco UCS fabric:DceSwSrvEp:peerPortId managed object property"
    ::= { cucsFabricDceSwSrvEpEntry 14 }

cucsFabricDceSwSrvEpPeerSlotId OBJECT-TYPE
    SYNTAX       Gauge32
    MAX-ACCESS   read-only
    STATUS       current
    DESCRIPTION
        "Cisco UCS fabric:DceSwSrvEp:peerSlotId managed object property"
    ::= { cucsFabricDceSwSrvEpEntry 15 }

cucsFabricDceSwSrvEpPortId OBJECT-TYPE
    SYNTAX       CucsFabricDceSwSrvEpPortId
    MAX-ACCESS   read-only
    STATUS       current
    DESCRIPTION
        "Cisco UCS fabric:DceSwSrvEp:portId managed object property"
    ::= { cucsFabricDceSwSrvEpEntry 16 }

cucsFabricDceSwSrvEpSlotId OBJECT-TYPE
    SYNTAX       CucsFabricDceSwSrvEpSlotId
    MAX-ACCESS   read-only
    STATUS       current
    DESCRIPTION
        "Cisco UCS fabric:DceSwSrvEp:slotId managed object property"
    ::= { cucsFabricDceSwSrvEpEntry 17 }

cucsFabricDceSwSrvEpSwitchId OBJECT-TYPE
    SYNTAX       CucsNetworkSwitchId
    MAX-ACCESS   read-only
    STATUS       current
    DESCRIPTION
        "Cisco UCS fabric:DceSwSrvEp:switchId managed object property"
    ::= { cucsFabricDceSwSrvEpEntry 18 }

cucsFabricDceSwSrvEpTransport OBJECT-TYPE
    SYNTAX       CucsFabricADceSwSrvEpTransport
    MAX-ACCESS   read-only
    STATUS       current
    DESCRIPTION
        "Cisco UCS fabric:DceSwSrvEp:transport managed object property"
    ::= { cucsFabricDceSwSrvEpEntry 19 }

cucsFabricDceSwSrvEpType OBJECT-TYPE
    SYNTAX       CucsFabricSwSrvEpType
    MAX-ACCESS   read-only
    STATUS       current
    DESCRIPTION
        "Cisco UCS fabric:DceSwSrvEp:type managed object property"
    ::= { cucsFabricDceSwSrvEpEntry 20 }

cucsFabricDceSwSrvEpUsrLbl OBJECT-TYPE
    SYNTAX       SnmpAdminString
    MAX-ACCESS   read-only
    STATUS       current
    DESCRIPTION
        "Cisco UCS fabric:DceSwSrvEp:usrLbl managed object property"
    ::= { cucsFabricDceSwSrvEpEntry 21 }

cucsFabricDceSwSrvEpPeerChassisId OBJECT-TYPE
    SYNTAX       Gauge32
    MAX-ACCESS   read-only
    STATUS       current
    DESCRIPTION
        "Cisco UCS fabric:DceSwSrvEp:peerChassisId managed
        object property"
    ::= { cucsFabricDceSwSrvEpEntry 22 }

cucsFabricDceSwSrvEpFltAggr OBJECT-TYPE
    SYNTAX       Unsigned64
    MAX-ACCESS   read-only
    STATUS       current
    DESCRIPTION
        "Cisco UCS fabric:DceSwSrvEp:fltAggr managed object property"
    ::= { cucsFabricDceSwSrvEpEntry 23 }

cucsFabricDceSwSrvPcTable OBJECT-TYPE
    SYNTAX           SEQUENCE OF CucsFabricDceSwSrvPcEntry
    MAX-ACCESS       not-accessible
    STATUS           current
    DESCRIPTION
        "Cisco UCS fabric:DceSwSrvPc managed object table"
    ::= { cucsFabricObjects 70 }

cucsFabricDceSwSrvPcEntry OBJECT-TYPE
    SYNTAX           CucsFabricDceSwSrvPcEntry
    MAX-ACCESS       not-accessible
    STATUS           current
    DESCRIPTION
        "Entry for the cucsFabricDceSwSrvPcTable table."
    INDEX { cucsFabricDceSwSrvPcInstanceId }
    ::= { cucsFabricDceSwSrvPcTable 1 }

CucsFabricDceSwSrvPcEntry ::= SEQUENCE {
    cucsFabricDceSwSrvPcInstanceId                                   CucsManagedObjectId,
    cucsFabricDceSwSrvPcDn                                           CucsManagedObjectDn,
    cucsFabricDceSwSrvPcRn                                           SnmpAdminString,
    cucsFabricDceSwSrvPcAdminState                                   CucsFabricAdminState,
    cucsFabricDceSwSrvPcChassisId                                    Gauge32,
    cucsFabricDceSwSrvPcEpDn                                         SnmpAdminString,
    cucsFabricDceSwSrvPcFltAggr                                      Unsigned64,
    cucsFabricDceSwSrvPcIfRole                                       CucsFabricSwSrvPcIfRole,
    cucsFabricDceSwSrvPcIfType                                       CucsFabricCIoEpIfType,
    cucsFabricDceSwSrvPcLocale                                       CucsFabricInternalPcLocale,
    cucsFabricDceSwSrvPcName                                         SnmpAdminString,
    cucsFabricDceSwSrvPcOperSpeed                                    CucsPortEthSpeed,
    cucsFabricDceSwSrvPcOperState                                    CucsNetworkPortOperState,
    cucsFabricDceSwSrvPcPeerDn                                       SnmpAdminString,
    cucsFabricDceSwSrvPcPortId                                       CucsFabricDceSwSrvPcPortId,
    cucsFabricDceSwSrvPcStateQual                                    SnmpAdminString,
    cucsFabricDceSwSrvPcSwitchId                                     CucsNetworkSwitchId,
    cucsFabricDceSwSrvPcTransport                                    CucsFabricDceSwSrvPcTransport,
    cucsFabricDceSwSrvPcType                                         CucsFabricSwSrvPcType
}

cucsFabricDceSwSrvPcInstanceId OBJECT-TYPE
    SYNTAX       CucsManagedObjectId
    MAX-ACCESS   not-accessible
    STATUS       current
    DESCRIPTION
        "Instance identifier of the managed object."
    ::= { cucsFabricDceSwSrvPcEntry 1 }

cucsFabricDceSwSrvPcDn OBJECT-TYPE
    SYNTAX       CucsManagedObjectDn
    MAX-ACCESS   read-only
    STATUS       current
    DESCRIPTION
        "Cisco UCS fabric:DceSwSrvPc:dn managed object property"
    ::= { cucsFabricDceSwSrvPcEntry 2 }

cucsFabricDceSwSrvPcRn OBJECT-TYPE
    SYNTAX       SnmpAdminString
    MAX-ACCESS   read-only
    STATUS       current
    DESCRIPTION
        "Cisco UCS fabric:DceSwSrvPc:rn managed object property"
    ::= { cucsFabricDceSwSrvPcEntry 3 }

cucsFabricDceSwSrvPcAdminState OBJECT-TYPE
    SYNTAX       CucsFabricAdminState
    MAX-ACCESS   read-only
    STATUS       current
    DESCRIPTION
        "Cisco UCS fabric:DceSwSrvPc:adminState managed object property"
    ::= { cucsFabricDceSwSrvPcEntry 4 }

cucsFabricDceSwSrvPcChassisId OBJECT-TYPE
    SYNTAX       Gauge32
    MAX-ACCESS   read-only
    STATUS       current
    DESCRIPTION
        "Cisco UCS fabric:DceSwSrvPc:chassisId managed object property"
    ::= { cucsFabricDceSwSrvPcEntry 5 }

cucsFabricDceSwSrvPcEpDn OBJECT-TYPE
    SYNTAX       SnmpAdminString
    MAX-ACCESS   read-only
    STATUS       current
    DESCRIPTION
        "Cisco UCS fabric:DceSwSrvPc:epDn managed object property"
    ::= { cucsFabricDceSwSrvPcEntry 6 }

cucsFabricDceSwSrvPcFltAggr OBJECT-TYPE
    SYNTAX       Unsigned64
    MAX-ACCESS   read-only
    STATUS       current
    DESCRIPTION
        "Cisco UCS fabric:DceSwSrvPc:fltAggr managed object property"
    ::= { cucsFabricDceSwSrvPcEntry 7 }

cucsFabricDceSwSrvPcIfRole OBJECT-TYPE
    SYNTAX       CucsFabricSwSrvPcIfRole
    MAX-ACCESS   read-only
    STATUS       current
    DESCRIPTION
        "Cisco UCS fabric:DceSwSrvPc:ifRole managed object property"
    ::= { cucsFabricDceSwSrvPcEntry 8 }

cucsFabricDceSwSrvPcIfType OBJECT-TYPE
    SYNTAX       CucsFabricCIoEpIfType
    MAX-ACCESS   read-only
    STATUS       current
    DESCRIPTION
        "Cisco UCS fabric:DceSwSrvPc:ifType managed object property"
    ::= { cucsFabricDceSwSrvPcEntry 9 }

cucsFabricDceSwSrvPcLocale OBJECT-TYPE
    SYNTAX       CucsFabricInternalPcLocale
    MAX-ACCESS   read-only
    STATUS       current
    DESCRIPTION
        "Cisco UCS fabric:DceSwSrvPc:locale managed object property"
    ::= { cucsFabricDceSwSrvPcEntry 10 }

cucsFabricDceSwSrvPcName OBJECT-TYPE
    SYNTAX       SnmpAdminString
    MAX-ACCESS   read-only
    STATUS       current
    DESCRIPTION
        "Cisco UCS fabric:DceSwSrvPc:name managed object property"
    ::= { cucsFabricDceSwSrvPcEntry 11 }

cucsFabricDceSwSrvPcOperSpeed OBJECT-TYPE
    SYNTAX       CucsPortEthSpeed
    MAX-ACCESS   read-only
    STATUS       current
    DESCRIPTION
        "Cisco UCS fabric:DceSwSrvPc:operSpeed managed object property"
    ::= { cucsFabricDceSwSrvPcEntry 12 }

cucsFabricDceSwSrvPcOperState OBJECT-TYPE
    SYNTAX       CucsNetworkPortOperState
    MAX-ACCESS   read-only
    STATUS       current
    DESCRIPTION
        "Cisco UCS fabric:DceSwSrvPc:operState managed object property"
    ::= { cucsFabricDceSwSrvPcEntry 13 }

cucsFabricDceSwSrvPcPeerDn OBJECT-TYPE
    SYNTAX       SnmpAdminString
    MAX-ACCESS   read-only
    STATUS       current
    DESCRIPTION
        "Cisco UCS fabric:DceSwSrvPc:peerDn managed object property"
    ::= { cucsFabricDceSwSrvPcEntry 14 }

cucsFabricDceSwSrvPcPortId OBJECT-TYPE
    SYNTAX       CucsFabricDceSwSrvPcPortId
    MAX-ACCESS   read-only
    STATUS       current
    DESCRIPTION
        "Cisco UCS fabric:DceSwSrvPc:portId managed object property"
    ::= { cucsFabricDceSwSrvPcEntry 15 }

cucsFabricDceSwSrvPcStateQual OBJECT-TYPE
    SYNTAX       SnmpAdminString
    MAX-ACCESS   read-only
    STATUS       current
    DESCRIPTION
        "Cisco UCS fabric:DceSwSrvPc:stateQual managed object property"
    ::= { cucsFabricDceSwSrvPcEntry 16 }

cucsFabricDceSwSrvPcSwitchId OBJECT-TYPE
    SYNTAX       CucsNetworkSwitchId
    MAX-ACCESS   read-only
    STATUS       current
    DESCRIPTION
        "Cisco UCS fabric:DceSwSrvPc:switchId managed object property"
    ::= { cucsFabricDceSwSrvPcEntry 17 }

cucsFabricDceSwSrvPcTransport OBJECT-TYPE
    SYNTAX       CucsFabricDceSwSrvPcTransport
    MAX-ACCESS   read-only
    STATUS       current
    DESCRIPTION
        "Cisco UCS fabric:DceSwSrvPc:transport managed object property"
    ::= { cucsFabricDceSwSrvPcEntry 18 }

cucsFabricDceSwSrvPcType OBJECT-TYPE
    SYNTAX       CucsFabricSwSrvPcType
    MAX-ACCESS   read-only
    STATUS       current
    DESCRIPTION
        "Cisco UCS fabric:DceSwSrvPc:type managed object property"
    ::= { cucsFabricDceSwSrvPcEntry 19 }

cucsFabricDceSwSrvPcEpTable OBJECT-TYPE
    SYNTAX           SEQUENCE OF CucsFabricDceSwSrvPcEpEntry
    MAX-ACCESS       not-accessible
    STATUS           current
    DESCRIPTION
        "Cisco UCS fabric:DceSwSrvPcEp managed object table"
    ::= { cucsFabricObjects 71 }

cucsFabricDceSwSrvPcEpEntry OBJECT-TYPE
    SYNTAX           CucsFabricDceSwSrvPcEpEntry
    MAX-ACCESS       not-accessible
    STATUS           current
    DESCRIPTION
        "Entry for the cucsFabricDceSwSrvPcEpTable table."
    INDEX { cucsFabricDceSwSrvPcEpInstanceId }
    ::= { cucsFabricDceSwSrvPcEpTable 1 }

CucsFabricDceSwSrvPcEpEntry ::= SEQUENCE {
    cucsFabricDceSwSrvPcEpInstanceId                                 CucsManagedObjectId,
    cucsFabricDceSwSrvPcEpDn                                         CucsManagedObjectDn,
    cucsFabricDceSwSrvPcEpRn                                         SnmpAdminString,
    cucsFabricDceSwSrvPcEpAdminState                                 CucsFabricInternalEpAdminState,
    cucsFabricDceSwSrvPcEpChassisId                                  Gauge32,
    cucsFabricDceSwSrvPcEpEpDn                                       SnmpAdminString,
    cucsFabricDceSwSrvPcEpFltAggr                                    Unsigned64,
    cucsFabricDceSwSrvPcEpIfRole                                     CucsFabricSwSrvEpIfRole,
    cucsFabricDceSwSrvPcEpIfType                                     CucsFabricPIoEpIfType,
    cucsFabricDceSwSrvPcEpLicGP                                      Unsigned64,
    cucsFabricDceSwSrvPcEpLicState                                   CucsLicenseState,
    cucsFabricDceSwSrvPcEpLocale                                     CucsFabricInternalEpLocale,
    cucsFabricDceSwSrvPcEpMembership                                 CucsFabricMembershipStatus,
    cucsFabricDceSwSrvPcEpName                                       SnmpAdminString,
    cucsFabricDceSwSrvPcEpPeerChassisId                              Gauge32,
    cucsFabricDceSwSrvPcEpPeerDn                                     SnmpAdminString,
    cucsFabricDceSwSrvPcEpPeerPortId                                 Gauge32,
    cucsFabricDceSwSrvPcEpPeerSlotId                                 Gauge32,
    cucsFabricDceSwSrvPcEpPortId                                     CucsFabricDceSwSrvPcEpPortId,
    cucsFabricDceSwSrvPcEpSlotId                                     CucsFabricDceSwSrvPcEpSlotId,
    cucsFabricDceSwSrvPcEpSwitchId                                   CucsNetworkSwitchId,
    cucsFabricDceSwSrvPcEpTransport                                  CucsFabricADceSwSrvEpTransport,
    cucsFabricDceSwSrvPcEpType                                       CucsFabricSwSrvEpType
}

cucsFabricDceSwSrvPcEpInstanceId OBJECT-TYPE
    SYNTAX       CucsManagedObjectId
    MAX-ACCESS   not-accessible
    STATUS       current
    DESCRIPTION
        "Instance identifier of the managed object."
    ::= { cucsFabricDceSwSrvPcEpEntry 1 }

cucsFabricDceSwSrvPcEpDn OBJECT-TYPE
    SYNTAX       CucsManagedObjectDn
    MAX-ACCESS   read-only
    STATUS       current
    DESCRIPTION
        "Cisco UCS fabric:DceSwSrvPcEp:dn managed object property"
    ::= { cucsFabricDceSwSrvPcEpEntry 2 }

cucsFabricDceSwSrvPcEpRn OBJECT-TYPE
    SYNTAX       SnmpAdminString
    MAX-ACCESS   read-only
    STATUS       current
    DESCRIPTION
        "Cisco UCS fabric:DceSwSrvPcEp:rn managed object property"
    ::= { cucsFabricDceSwSrvPcEpEntry 3 }

cucsFabricDceSwSrvPcEpAdminState OBJECT-TYPE
    SYNTAX       CucsFabricInternalEpAdminState
    MAX-ACCESS   read-only
    STATUS       current
    DESCRIPTION
        "Cisco UCS fabric:DceSwSrvPcEp:adminState managed object property"
    ::= { cucsFabricDceSwSrvPcEpEntry 4 }

cucsFabricDceSwSrvPcEpChassisId OBJECT-TYPE
    SYNTAX       Gauge32
    MAX-ACCESS   read-only
    STATUS       current
    DESCRIPTION
        "Cisco UCS fabric:DceSwSrvPcEp:chassisId managed object property"
    ::= { cucsFabricDceSwSrvPcEpEntry 5 }

cucsFabricDceSwSrvPcEpEpDn OBJECT-TYPE
    SYNTAX       SnmpAdminString
    MAX-ACCESS   read-only
    STATUS       current
    DESCRIPTION
        "Cisco UCS fabric:DceSwSrvPcEp:epDn managed object property"
    ::= { cucsFabricDceSwSrvPcEpEntry 6 }

cucsFabricDceSwSrvPcEpFltAggr OBJECT-TYPE
    SYNTAX       Unsigned64
    MAX-ACCESS   read-only
    STATUS       current
    DESCRIPTION
        "Cisco UCS fabric:DceSwSrvPcEp:fltAggr managed object property"
    ::= { cucsFabricDceSwSrvPcEpEntry 7 }

cucsFabricDceSwSrvPcEpIfRole OBJECT-TYPE
    SYNTAX       CucsFabricSwSrvEpIfRole
    MAX-ACCESS   read-only
    STATUS       current
    DESCRIPTION
        "Cisco UCS fabric:DceSwSrvPcEp:ifRole managed object property"
    ::= { cucsFabricDceSwSrvPcEpEntry 8 }

cucsFabricDceSwSrvPcEpIfType OBJECT-TYPE
    SYNTAX       CucsFabricPIoEpIfType
    MAX-ACCESS   read-only
    STATUS       current
    DESCRIPTION
        "Cisco UCS fabric:DceSwSrvPcEp:ifType managed object property"
    ::= { cucsFabricDceSwSrvPcEpEntry 9 }

cucsFabricDceSwSrvPcEpLicGP OBJECT-TYPE
    SYNTAX       Unsigned64
    MAX-ACCESS   read-only
    STATUS       current
    DESCRIPTION
        "Cisco UCS fabric:DceSwSrvPcEp:licGP managed object property"
    ::= { cucsFabricDceSwSrvPcEpEntry 10 }

cucsFabricDceSwSrvPcEpLicState OBJECT-TYPE
    SYNTAX       CucsLicenseState
    MAX-ACCESS   read-only
    STATUS       current
    DESCRIPTION
        "Cisco UCS fabric:DceSwSrvPcEp:licState managed object property"
    ::= { cucsFabricDceSwSrvPcEpEntry 11 }

cucsFabricDceSwSrvPcEpLocale OBJECT-TYPE
    SYNTAX       CucsFabricInternalEpLocale
    MAX-ACCESS   read-only
    STATUS       current
    DESCRIPTION
        "Cisco UCS fabric:DceSwSrvPcEp:locale managed object property"
    ::= { cucsFabricDceSwSrvPcEpEntry 12 }

cucsFabricDceSwSrvPcEpMembership OBJECT-TYPE
    SYNTAX       CucsFabricMembershipStatus
    MAX-ACCESS   read-only
    STATUS       current
    DESCRIPTION
        "Cisco UCS fabric:DceSwSrvPcEp:membership managed object property"
    ::= { cucsFabricDceSwSrvPcEpEntry 13 }

cucsFabricDceSwSrvPcEpName OBJECT-TYPE
    SYNTAX       SnmpAdminString
    MAX-ACCESS   read-only
    STATUS       current
    DESCRIPTION
        "Cisco UCS fabric:DceSwSrvPcEp:name managed object property"
    ::= { cucsFabricDceSwSrvPcEpEntry 14 }

cucsFabricDceSwSrvPcEpPeerChassisId OBJECT-TYPE
    SYNTAX       Gauge32
    MAX-ACCESS   read-only
    STATUS       current
    DESCRIPTION
        "Cisco UCS fabric:DceSwSrvPcEp:peerChassisId managed
        object property"
    ::= { cucsFabricDceSwSrvPcEpEntry 15 }

cucsFabricDceSwSrvPcEpPeerDn OBJECT-TYPE
    SYNTAX       SnmpAdminString
    MAX-ACCESS   read-only
    STATUS       current
    DESCRIPTION
        "Cisco UCS fabric:DceSwSrvPcEp:peerDn managed object property"
    ::= { cucsFabricDceSwSrvPcEpEntry 16 }

cucsFabricDceSwSrvPcEpPeerPortId OBJECT-TYPE
    SYNTAX       Gauge32
    MAX-ACCESS   read-only
    STATUS       current
    DESCRIPTION
        "Cisco UCS fabric:DceSwSrvPcEp:peerPortId managed object property"
    ::= { cucsFabricDceSwSrvPcEpEntry 17 }

cucsFabricDceSwSrvPcEpPeerSlotId OBJECT-TYPE
    SYNTAX       Gauge32
    MAX-ACCESS   read-only
    STATUS       current
    DESCRIPTION
        "Cisco UCS fabric:DceSwSrvPcEp:peerSlotId managed object property"
    ::= { cucsFabricDceSwSrvPcEpEntry 18 }

cucsFabricDceSwSrvPcEpPortId OBJECT-TYPE
    SYNTAX       CucsFabricDceSwSrvPcEpPortId
    MAX-ACCESS   read-only
    STATUS       current
    DESCRIPTION
        "Cisco UCS fabric:DceSwSrvPcEp:portId managed object property"
    ::= { cucsFabricDceSwSrvPcEpEntry 19 }

cucsFabricDceSwSrvPcEpSlotId OBJECT-TYPE
    SYNTAX       CucsFabricDceSwSrvPcEpSlotId
    MAX-ACCESS   read-only
    STATUS       current
    DESCRIPTION
        "Cisco UCS fabric:DceSwSrvPcEp:slotId managed object property"
    ::= { cucsFabricDceSwSrvPcEpEntry 20 }

cucsFabricDceSwSrvPcEpSwitchId OBJECT-TYPE
    SYNTAX       CucsNetworkSwitchId
    MAX-ACCESS   read-only
    STATUS       current
    DESCRIPTION
        "Cisco UCS fabric:DceSwSrvPcEp:switchId managed object property"
    ::= { cucsFabricDceSwSrvPcEpEntry 21 }

cucsFabricDceSwSrvPcEpTransport OBJECT-TYPE
    SYNTAX       CucsFabricADceSwSrvEpTransport
    MAX-ACCESS   read-only
    STATUS       current
    DESCRIPTION
        "Cisco UCS fabric:DceSwSrvPcEp:transport managed object property"
    ::= { cucsFabricDceSwSrvPcEpEntry 22 }

cucsFabricDceSwSrvPcEpType OBJECT-TYPE
    SYNTAX       CucsFabricSwSrvEpType
    MAX-ACCESS   read-only
    STATUS       current
    DESCRIPTION
        "Cisco UCS fabric:DceSwSrvPcEp:type managed object property"
    ::= { cucsFabricDceSwSrvPcEpEntry 23 }

cucsFabricEpTable OBJECT-TYPE
    SYNTAX           SEQUENCE OF CucsFabricEpEntry
    MAX-ACCESS       not-accessible
    STATUS           current
    DESCRIPTION
        "Cisco UCS fabric:Ep managed object table"
    ::= { cucsFabricObjects 8 }

cucsFabricEpEntry OBJECT-TYPE
    SYNTAX           CucsFabricEpEntry
    MAX-ACCESS       not-accessible
    STATUS           current
    DESCRIPTION
        "Entry for the cucsFabricEpTable table."
    INDEX { cucsFabricEpInstanceId }
    ::= { cucsFabricEpTable 1 }

CucsFabricEpEntry ::= SEQUENCE {
    cucsFabricEpInstanceId                                           CucsManagedObjectId,
    cucsFabricEpDn                                                   CucsManagedObjectDn,
    cucsFabricEpRn                                                   SnmpAdminString
}

cucsFabricEpInstanceId OBJECT-TYPE
    SYNTAX       CucsManagedObjectId
    MAX-ACCESS   not-accessible
    STATUS       current
    DESCRIPTION
        "Instance identifier of the managed object."
    ::= { cucsFabricEpEntry 1 }

cucsFabricEpDn OBJECT-TYPE
    SYNTAX       CucsManagedObjectDn
    MAX-ACCESS   read-only
    STATUS       current
    DESCRIPTION
        "Cisco UCS fabric:Ep:dn managed object property"
    ::= { cucsFabricEpEntry 2 }

cucsFabricEpRn OBJECT-TYPE
    SYNTAX       SnmpAdminString
    MAX-ACCESS   read-only
    STATUS       current
    DESCRIPTION
        "Cisco UCS fabric:Ep:rn managed object property"
    ::= { cucsFabricEpEntry 3 }

cucsFabricEpMgrTable OBJECT-TYPE
    SYNTAX           SEQUENCE OF CucsFabricEpMgrEntry
    MAX-ACCESS       not-accessible
    STATUS           current
    DESCRIPTION
        "Cisco UCS fabric:EpMgr managed object table"
    ::= { cucsFabricObjects 72 }

cucsFabricEpMgrEntry OBJECT-TYPE
    SYNTAX           CucsFabricEpMgrEntry
    MAX-ACCESS       not-accessible
    STATUS           current
    DESCRIPTION
        "Entry for the cucsFabricEpMgrTable table."
    INDEX { cucsFabricEpMgrInstanceId }
    ::= { cucsFabricEpMgrTable 1 }

CucsFabricEpMgrEntry ::= SEQUENCE {
    cucsFabricEpMgrInstanceId                                        CucsManagedObjectId,
    cucsFabricEpMgrDn                                                CucsManagedObjectDn,
    cucsFabricEpMgrRn                                                SnmpAdminString,
    cucsFabricEpMgrConfMode                                          CucsFabricConfMode,
    cucsFabricEpMgrFltAggr                                           Unsigned64,
    cucsFabricEpMgrFsmDescr                                          SnmpAdminString,
    cucsFabricEpMgrFsmFlags                                          SnmpAdminString,
    cucsFabricEpMgrFsmPrev                                           SnmpAdminString,
    cucsFabricEpMgrFsmProgr                                          Gauge32,
    cucsFabricEpMgrFsmRmtInvErrCode                                  Gauge32,
    cucsFabricEpMgrFsmRmtInvErrDescr                                 SnmpAdminString,
    cucsFabricEpMgrFsmRmtInvRslt                                     CucsConditionRemoteInvRslt,
    cucsFabricEpMgrFsmStageDescr                                     SnmpAdminString,
    cucsFabricEpMgrFsmStamp                                          DateAndTime,
    cucsFabricEpMgrFsmStatus                                         SnmpAdminString,
    cucsFabricEpMgrFsmTry                                            Gauge32,
    cucsFabricEpMgrId                                                CucsNetworkSwitchId
}

cucsFabricEpMgrInstanceId OBJECT-TYPE
    SYNTAX       CucsManagedObjectId
    MAX-ACCESS   not-accessible
    STATUS       current
    DESCRIPTION
        "Instance identifier of the managed object."
    ::= { cucsFabricEpMgrEntry 1 }

cucsFabricEpMgrDn OBJECT-TYPE
    SYNTAX       CucsManagedObjectDn
    MAX-ACCESS   read-only
    STATUS       current
    DESCRIPTION
        "Cisco UCS fabric:EpMgr:dn managed object property"
    ::= { cucsFabricEpMgrEntry 2 }

cucsFabricEpMgrRn OBJECT-TYPE
    SYNTAX       SnmpAdminString
    MAX-ACCESS   read-only
    STATUS       current
    DESCRIPTION
        "Cisco UCS fabric:EpMgr:rn managed object property"
    ::= { cucsFabricEpMgrEntry 3 }

cucsFabricEpMgrConfMode OBJECT-TYPE
    SYNTAX       CucsFabricConfMode
    MAX-ACCESS   read-only
    STATUS       current
    DESCRIPTION
        "Cisco UCS fabric:EpMgr:confMode managed object property"
    ::= { cucsFabricEpMgrEntry 5 }

cucsFabricEpMgrFltAggr OBJECT-TYPE
    SYNTAX       Unsigned64
    MAX-ACCESS   read-only
    STATUS       current
    DESCRIPTION
        "Cisco UCS fabric:EpMgr:fltAggr managed object property"
    ::= { cucsFabricEpMgrEntry 6 }

cucsFabricEpMgrFsmDescr OBJECT-TYPE
    SYNTAX       SnmpAdminString
    MAX-ACCESS   read-only
    STATUS       current
    DESCRIPTION
        "Cisco UCS fabric:EpMgr:fsmDescr managed object property"
    ::= { cucsFabricEpMgrEntry 7 }

cucsFabricEpMgrFsmFlags OBJECT-TYPE
    SYNTAX       SnmpAdminString
    MAX-ACCESS   read-only
    STATUS       current
    DESCRIPTION
        "Cisco UCS fabric:EpMgr:fsmFlags managed object property"
    ::= { cucsFabricEpMgrEntry 8 }

cucsFabricEpMgrFsmPrev OBJECT-TYPE
    SYNTAX       SnmpAdminString
    MAX-ACCESS   read-only
    STATUS       current
    DESCRIPTION
        "Cisco UCS fabric:EpMgr:fsmPrev managed object property"
    ::= { cucsFabricEpMgrEntry 9 }

cucsFabricEpMgrFsmProgr OBJECT-TYPE
    SYNTAX       Gauge32
    MAX-ACCESS   read-only
    STATUS       current
    DESCRIPTION
        "Cisco UCS fabric:EpMgr:fsmProgr managed object property"
    ::= { cucsFabricEpMgrEntry 10 }

cucsFabricEpMgrFsmRmtInvErrCode OBJECT-TYPE
    SYNTAX       Gauge32
    MAX-ACCESS   read-only
    STATUS       current
    DESCRIPTION
        "Cisco UCS fabric:EpMgr:fsmRmtInvErrCode managed object property"
    ::= { cucsFabricEpMgrEntry 11 }

cucsFabricEpMgrFsmRmtInvErrDescr OBJECT-TYPE
    SYNTAX       SnmpAdminString
    MAX-ACCESS   read-only
    STATUS       current
    DESCRIPTION
        "Cisco UCS fabric:EpMgr:fsmRmtInvErrDescr managed object property"
    ::= { cucsFabricEpMgrEntry 12 }

cucsFabricEpMgrFsmRmtInvRslt OBJECT-TYPE
    SYNTAX       CucsConditionRemoteInvRslt
    MAX-ACCESS   read-only
    STATUS       current
    DESCRIPTION
        "Cisco UCS fabric:EpMgr:fsmRmtInvRslt managed object property"
    ::= { cucsFabricEpMgrEntry 13 }

cucsFabricEpMgrFsmStageDescr OBJECT-TYPE
    SYNTAX       SnmpAdminString
    MAX-ACCESS   read-only
    STATUS       current
    DESCRIPTION
        "Cisco UCS fabric:EpMgr:fsmStageDescr managed object property"
    ::= { cucsFabricEpMgrEntry 14 }

cucsFabricEpMgrFsmStamp OBJECT-TYPE
    SYNTAX       DateAndTime
    MAX-ACCESS   read-only
    STATUS       current
    DESCRIPTION
        "Cisco UCS fabric:EpMgr:fsmStamp managed object property"
    ::= { cucsFabricEpMgrEntry 15 }

cucsFabricEpMgrFsmStatus OBJECT-TYPE
    SYNTAX       SnmpAdminString
    MAX-ACCESS   read-only
    STATUS       current
    DESCRIPTION
        "Cisco UCS fabric:EpMgr:fsmStatus managed object property"
    ::= { cucsFabricEpMgrEntry 16 }

cucsFabricEpMgrFsmTry OBJECT-TYPE
    SYNTAX       Gauge32
    MAX-ACCESS   read-only
    STATUS       current
    DESCRIPTION
        "Cisco UCS fabric:EpMgr:fsmTry managed object property"
    ::= { cucsFabricEpMgrEntry 17 }

cucsFabricEpMgrId OBJECT-TYPE
    SYNTAX       CucsNetworkSwitchId
    MAX-ACCESS   read-only
    STATUS       current
    DESCRIPTION
        "Cisco UCS fabric:EpMgr:id managed object property"
    ::= { cucsFabricEpMgrEntry 18 }

cucsFabricEpMgrFsmTaskTable OBJECT-TYPE
    SYNTAX           SEQUENCE OF CucsFabricEpMgrFsmTaskEntry
    MAX-ACCESS       not-accessible
    STATUS           current
    DESCRIPTION
        "Cisco UCS fabric:EpMgrFsmTask managed object table"
    ::= { cucsFabricObjects 73 }

cucsFabricEpMgrFsmTaskEntry OBJECT-TYPE
    SYNTAX           CucsFabricEpMgrFsmTaskEntry
    MAX-ACCESS       not-accessible
    STATUS           current
    DESCRIPTION
        "Entry for the cucsFabricEpMgrFsmTaskTable table."
    INDEX { cucsFabricEpMgrFsmTaskInstanceId }
    ::= { cucsFabricEpMgrFsmTaskTable 1 }

CucsFabricEpMgrFsmTaskEntry ::= SEQUENCE {
    cucsFabricEpMgrFsmTaskInstanceId                                 CucsManagedObjectId,
    cucsFabricEpMgrFsmTaskDn                                         CucsManagedObjectDn,
    cucsFabricEpMgrFsmTaskRn                                         SnmpAdminString,
    cucsFabricEpMgrFsmTaskCompletion                                 CucsFsmCompletion,
    cucsFabricEpMgrFsmTaskFlags                                      CucsFabricEpMgrFsmTaskFlags,
    cucsFabricEpMgrFsmTaskItem                                       CucsFabricEpMgrFsmTaskItem,
    cucsFabricEpMgrFsmTaskSeqId                                      Gauge32
}

cucsFabricEpMgrFsmTaskInstanceId OBJECT-TYPE
    SYNTAX       CucsManagedObjectId
    MAX-ACCESS   not-accessible
    STATUS       current
    DESCRIPTION
        "Instance identifier of the managed object."
    ::= { cucsFabricEpMgrFsmTaskEntry 1 }

cucsFabricEpMgrFsmTaskDn OBJECT-TYPE
    SYNTAX       CucsManagedObjectDn
    MAX-ACCESS   read-only
    STATUS       current
    DESCRIPTION
        "Cisco UCS fabric:EpMgrFsmTask:dn managed object property"
    ::= { cucsFabricEpMgrFsmTaskEntry 2 }

cucsFabricEpMgrFsmTaskRn OBJECT-TYPE
    SYNTAX       SnmpAdminString
    MAX-ACCESS   read-only
    STATUS       current
    DESCRIPTION
        "Cisco UCS fabric:EpMgrFsmTask:rn managed object property"
    ::= { cucsFabricEpMgrFsmTaskEntry 3 }

cucsFabricEpMgrFsmTaskCompletion OBJECT-TYPE
    SYNTAX       CucsFsmCompletion
    MAX-ACCESS   read-only
    STATUS       current
    DESCRIPTION
        "Cisco UCS fabric:EpMgrFsmTask:completion managed object property"
    ::= { cucsFabricEpMgrFsmTaskEntry 4 }

cucsFabricEpMgrFsmTaskFlags OBJECT-TYPE
    SYNTAX       CucsFabricEpMgrFsmTaskFlags
    MAX-ACCESS   read-only
    STATUS       current
    DESCRIPTION
        "Cisco UCS fabric:EpMgrFsmTask:flags managed object property"
    ::= { cucsFabricEpMgrFsmTaskEntry 5 }

cucsFabricEpMgrFsmTaskItem OBJECT-TYPE
    SYNTAX       CucsFabricEpMgrFsmTaskItem
    MAX-ACCESS   read-only
    STATUS       current
    DESCRIPTION
        "Cisco UCS fabric:EpMgrFsmTask:item managed object property"
    ::= { cucsFabricEpMgrFsmTaskEntry 6 }

cucsFabricEpMgrFsmTaskSeqId OBJECT-TYPE
    SYNTAX       Gauge32
    MAX-ACCESS   read-only
    STATUS       current
    DESCRIPTION
        "Cisco UCS fabric:EpMgrFsmTask:seqId managed object property"
    ::= { cucsFabricEpMgrFsmTaskEntry 7 }

cucsFabricEthEstcTable OBJECT-TYPE
    SYNTAX           SEQUENCE OF CucsFabricEthEstcEntry
    MAX-ACCESS       not-accessible
    STATUS           current
    DESCRIPTION
        "Cisco UCS fabric:EthEstc managed object table"
    ::= { cucsFabricObjects 9 }

cucsFabricEthEstcEntry OBJECT-TYPE
    SYNTAX           CucsFabricEthEstcEntry
    MAX-ACCESS       not-accessible
    STATUS           current
    DESCRIPTION
        "Entry for the cucsFabricEthEstcTable table."
    INDEX { cucsFabricEthEstcInstanceId }
    ::= { cucsFabricEthEstcTable 1 }

CucsFabricEthEstcEntry ::= SEQUENCE {
    cucsFabricEthEstcInstanceId                                      CucsManagedObjectId,
    cucsFabricEthEstcDn                                              CucsManagedObjectDn,
    cucsFabricEthEstcRn                                              SnmpAdminString,
    cucsFabricEthEstcId                                              CucsNetworkSwitchId,
    cucsFabricEthEstcLocale                                          CucsFabricExternalLocale,
    cucsFabricEthEstcName                                            SnmpAdminString,
    cucsFabricEthEstcTransport                                       CucsFabricEthEstcTransport,
    cucsFabricEthEstcType                                            CucsFabricEthEstcType
}

cucsFabricEthEstcInstanceId OBJECT-TYPE
    SYNTAX       CucsManagedObjectId
    MAX-ACCESS   not-accessible
    STATUS       current
    DESCRIPTION
        "Instance identifier of the managed object."
    ::= { cucsFabricEthEstcEntry 1 }

cucsFabricEthEstcDn OBJECT-TYPE
    SYNTAX       CucsManagedObjectDn
    MAX-ACCESS   read-only
    STATUS       current
    DESCRIPTION
        "Cisco UCS fabric:EthEstc:dn managed object property"
    ::= { cucsFabricEthEstcEntry 2 }

cucsFabricEthEstcRn OBJECT-TYPE
    SYNTAX       SnmpAdminString
    MAX-ACCESS   read-only
    STATUS       current
    DESCRIPTION
        "Cisco UCS fabric:EthEstc:rn managed object property"
    ::= { cucsFabricEthEstcEntry 3 }

cucsFabricEthEstcId OBJECT-TYPE
    SYNTAX       CucsNetworkSwitchId
    MAX-ACCESS   read-only
    STATUS       current
    DESCRIPTION
        "Cisco UCS fabric:EthEstc:id managed object property"
    ::= { cucsFabricEthEstcEntry 4 }

cucsFabricEthEstcLocale OBJECT-TYPE
    SYNTAX       CucsFabricExternalLocale
    MAX-ACCESS   read-only
    STATUS       current
    DESCRIPTION
        "Cisco UCS fabric:EthEstc:locale managed object property"
    ::= { cucsFabricEthEstcEntry 5 }

cucsFabricEthEstcName OBJECT-TYPE
    SYNTAX       SnmpAdminString
    MAX-ACCESS   read-only
    STATUS       current
    DESCRIPTION
        "Cisco UCS fabric:EthEstc:name managed object property"
    ::= { cucsFabricEthEstcEntry 6 }

cucsFabricEthEstcTransport OBJECT-TYPE
    SYNTAX       CucsFabricEthEstcTransport
    MAX-ACCESS   read-only
    STATUS       current
    DESCRIPTION
        "Cisco UCS fabric:EthEstc:transport managed object property"
    ::= { cucsFabricEthEstcEntry 7 }

cucsFabricEthEstcType OBJECT-TYPE
    SYNTAX       CucsFabricEthEstcType
    MAX-ACCESS   read-only
    STATUS       current
    DESCRIPTION
        "Cisco UCS fabric:EthEstc:type managed object property"
    ::= { cucsFabricEthEstcEntry 8 }

cucsFabricEthEstcCloudTable OBJECT-TYPE
    SYNTAX           SEQUENCE OF CucsFabricEthEstcCloudEntry
    MAX-ACCESS       not-accessible
    STATUS           current
    DESCRIPTION
        "Cisco UCS fabric:EthEstcCloud managed object table"
    ::= { cucsFabricObjects 10 }

cucsFabricEthEstcCloudEntry OBJECT-TYPE
    SYNTAX           CucsFabricEthEstcCloudEntry
    MAX-ACCESS       not-accessible
    STATUS           current
    DESCRIPTION
        "Entry for the cucsFabricEthEstcCloudTable table."
    INDEX { cucsFabricEthEstcCloudInstanceId }
    ::= { cucsFabricEthEstcCloudTable 1 }

CucsFabricEthEstcCloudEntry ::= SEQUENCE {
    cucsFabricEthEstcCloudInstanceId                                 CucsManagedObjectId,
    cucsFabricEthEstcCloudDn                                         CucsManagedObjectDn,
    cucsFabricEthEstcCloudRn                                         SnmpAdminString
}

cucsFabricEthEstcCloudInstanceId OBJECT-TYPE
    SYNTAX       CucsManagedObjectId
    MAX-ACCESS   not-accessible
    STATUS       current
    DESCRIPTION
        "Instance identifier of the managed object."
    ::= { cucsFabricEthEstcCloudEntry 1 }

cucsFabricEthEstcCloudDn OBJECT-TYPE
    SYNTAX       CucsManagedObjectDn
    MAX-ACCESS   read-only
    STATUS       current
    DESCRIPTION
        "Cisco UCS fabric:EthEstcCloud:dn managed object property"
    ::= { cucsFabricEthEstcCloudEntry 2 }

cucsFabricEthEstcCloudRn OBJECT-TYPE
    SYNTAX       SnmpAdminString
    MAX-ACCESS   read-only
    STATUS       current
    DESCRIPTION
        "Cisco UCS fabric:EthEstcCloud:rn managed object property"
    ::= { cucsFabricEthEstcCloudEntry 3 }

cucsFabricEthEstcEpTable OBJECT-TYPE
    SYNTAX           SEQUENCE OF CucsFabricEthEstcEpEntry
    MAX-ACCESS       not-accessible
    STATUS           current
    DESCRIPTION
        "Cisco UCS fabric:EthEstcEp managed object table"
    ::= { cucsFabricObjects 11 }

cucsFabricEthEstcEpEntry OBJECT-TYPE
    SYNTAX           CucsFabricEthEstcEpEntry
    MAX-ACCESS       not-accessible
    STATUS           current
    DESCRIPTION
        "Entry for the cucsFabricEthEstcEpTable table."
    INDEX { cucsFabricEthEstcEpInstanceId }
    ::= { cucsFabricEthEstcEpTable 1 }

CucsFabricEthEstcEpEntry ::= SEQUENCE {
    cucsFabricEthEstcEpInstanceId                                    CucsManagedObjectId,
    cucsFabricEthEstcEpDn                                            CucsManagedObjectDn,
    cucsFabricEthEstcEpRn                                            SnmpAdminString,
    cucsFabricEthEstcEpAdminState                                    CucsFabricExternalEpAdminState,
    cucsFabricEthEstcEpChassisId                                     Gauge32,
    cucsFabricEthEstcEpConfigState                                   CucsFabricConfigState,
    cucsFabricEthEstcEpEpDn                                          SnmpAdminString,
    cucsFabricEthEstcEpIfRole                                        CucsFabricAEthEstcEpIfRole,
    cucsFabricEthEstcEpIfType                                        CucsFabricPIoEpIfType,
    cucsFabricEthEstcEpLicGP                                         Unsigned64,
    cucsFabricEthEstcEpLicState                                      CucsLicenseState,
    cucsFabricEthEstcEpLocale                                        CucsFabricExternalEpLocale,
    cucsFabricEthEstcEpName                                          SnmpAdminString,
    cucsFabricEthEstcEpPeerDn                                        SnmpAdminString,
    cucsFabricEthEstcEpPeerPortId                                    Gauge32,
    cucsFabricEthEstcEpPeerSlotId                                    Gauge32,
    cucsFabricEthEstcEpPinGroupName                                  SnmpAdminString,
    cucsFabricEthEstcEpPortId                                        CucsFabricEthEstcEpPortId,
    cucsFabricEthEstcEpPortMode                                      CucsFabricEthEstcPortMode,
    cucsFabricEthEstcEpPrio                                          CucsFabricEthEstcEpPrio,
    cucsFabricEthEstcEpSlotId                                        CucsFabricEthEstcEpSlotId,
    cucsFabricEthEstcEpSwitchId                                      CucsNetworkSwitchId,
    cucsFabricEthEstcEpTransport                                     CucsFabricEthEstcEpTransport,
    cucsFabricEthEstcEpType                                          CucsFabricEthEstcEpType,
    cucsFabricEthEstcEpUsrLbl                                        SnmpAdminString,
    cucsFabricEthEstcEpAdminSpeed                                    CucsPortEthSpeed,
    cucsFabricEthEstcEpPeerChassisId                                 Gauge32,
    cucsFabricEthEstcEpFltAggr                                       Unsigned64,
    cucsFabricEthEstcEpNwCtrlPolicyName                              SnmpAdminString,
    cucsFabricEthEstcEpOperNwCtrlPolicyName                          SnmpAdminString
}

cucsFabricEthEstcEpInstanceId OBJECT-TYPE
    SYNTAX       CucsManagedObjectId
    MAX-ACCESS   not-accessible
    STATUS       current
    DESCRIPTION
        "Instance identifier of the managed object."
    ::= { cucsFabricEthEstcEpEntry 1 }

cucsFabricEthEstcEpDn OBJECT-TYPE
    SYNTAX       CucsManagedObjectDn
    MAX-ACCESS   read-only
    STATUS       current
    DESCRIPTION
        "Cisco UCS fabric:EthEstcEp:dn managed object property"
    ::= { cucsFabricEthEstcEpEntry 2 }

cucsFabricEthEstcEpRn OBJECT-TYPE
    SYNTAX       SnmpAdminString
    MAX-ACCESS   read-only
    STATUS       current
    DESCRIPTION
        "Cisco UCS fabric:EthEstcEp:rn managed object property"
    ::= { cucsFabricEthEstcEpEntry 3 }

cucsFabricEthEstcEpAdminState OBJECT-TYPE
    SYNTAX       CucsFabricExternalEpAdminState
    MAX-ACCESS   read-only
    STATUS       current
    DESCRIPTION
        "Cisco UCS fabric:EthEstcEp:adminState managed object property"
    ::= { cucsFabricEthEstcEpEntry 4 }

cucsFabricEthEstcEpChassisId OBJECT-TYPE
    SYNTAX       Gauge32
    MAX-ACCESS   read-only
    STATUS       current
    DESCRIPTION
        "Cisco UCS fabric:EthEstcEp:chassisId managed object property"
    ::= { cucsFabricEthEstcEpEntry 5 }

cucsFabricEthEstcEpConfigState OBJECT-TYPE
    SYNTAX       CucsFabricConfigState
    MAX-ACCESS   read-only
    STATUS       current
    DESCRIPTION
        "Cisco UCS fabric:EthEstcEp:configState managed object property"
    ::= { cucsFabricEthEstcEpEntry 6 }

cucsFabricEthEstcEpEpDn OBJECT-TYPE
    SYNTAX       SnmpAdminString
    MAX-ACCESS   read-only
    STATUS       current
    DESCRIPTION
        "Cisco UCS fabric:EthEstcEp:epDn managed object property"
    ::= { cucsFabricEthEstcEpEntry 7 }

cucsFabricEthEstcEpIfRole OBJECT-TYPE
    SYNTAX       CucsFabricAEthEstcEpIfRole
    MAX-ACCESS   read-only
    STATUS       current
    DESCRIPTION
        "Cisco UCS fabric:EthEstcEp:ifRole managed object property"
    ::= { cucsFabricEthEstcEpEntry 8 }

cucsFabricEthEstcEpIfType OBJECT-TYPE
    SYNTAX       CucsFabricPIoEpIfType
    MAX-ACCESS   read-only
    STATUS       current
    DESCRIPTION
        "Cisco UCS fabric:EthEstcEp:ifType managed object property"
    ::= { cucsFabricEthEstcEpEntry 9 }

cucsFabricEthEstcEpLicGP OBJECT-TYPE
    SYNTAX       Unsigned64
    MAX-ACCESS   read-only
    STATUS       current
    DESCRIPTION
        "Cisco UCS fabric:EthEstcEp:licGP managed object property"
    ::= { cucsFabricEthEstcEpEntry 10 }

cucsFabricEthEstcEpLicState OBJECT-TYPE
    SYNTAX       CucsLicenseState
    MAX-ACCESS   read-only
    STATUS       current
    DESCRIPTION
        "Cisco UCS fabric:EthEstcEp:licState managed object property"
    ::= { cucsFabricEthEstcEpEntry 11 }

cucsFabricEthEstcEpLocale OBJECT-TYPE
    SYNTAX       CucsFabricExternalEpLocale
    MAX-ACCESS   read-only
    STATUS       current
    DESCRIPTION
        "Cisco UCS fabric:EthEstcEp:locale managed object property"
    ::= { cucsFabricEthEstcEpEntry 12 }

cucsFabricEthEstcEpName OBJECT-TYPE
    SYNTAX       SnmpAdminString
    MAX-ACCESS   read-only
    STATUS       current
    DESCRIPTION
        "Cisco UCS fabric:EthEstcEp:name managed object property"
    ::= { cucsFabricEthEstcEpEntry 13 }

cucsFabricEthEstcEpPeerDn OBJECT-TYPE
    SYNTAX       SnmpAdminString
    MAX-ACCESS   read-only
    STATUS       current
    DESCRIPTION
        "Cisco UCS fabric:EthEstcEp:peerDn managed object property"
    ::= { cucsFabricEthEstcEpEntry 14 }

cucsFabricEthEstcEpPeerPortId OBJECT-TYPE
    SYNTAX       Gauge32
    MAX-ACCESS   read-only
    STATUS       current
    DESCRIPTION
        "Cisco UCS fabric:EthEstcEp:peerPortId managed object property"
    ::= { cucsFabricEthEstcEpEntry 15 }

cucsFabricEthEstcEpPeerSlotId OBJECT-TYPE
    SYNTAX       Gauge32
    MAX-ACCESS   read-only
    STATUS       current
    DESCRIPTION
        "Cisco UCS fabric:EthEstcEp:peerSlotId managed object property"
    ::= { cucsFabricEthEstcEpEntry 16 }

cucsFabricEthEstcEpPinGroupName OBJECT-TYPE
    SYNTAX       SnmpAdminString
    MAX-ACCESS   read-only
    STATUS       current
    DESCRIPTION
        "Cisco UCS fabric:EthEstcEp:pinGroupName managed object property"
    ::= { cucsFabricEthEstcEpEntry 17 }

cucsFabricEthEstcEpPortId OBJECT-TYPE
    SYNTAX       CucsFabricEthEstcEpPortId
    MAX-ACCESS   read-only
    STATUS       current
    DESCRIPTION
        "Cisco UCS fabric:EthEstcEp:portId managed object property"
    ::= { cucsFabricEthEstcEpEntry 18 }

cucsFabricEthEstcEpPortMode OBJECT-TYPE
    SYNTAX       CucsFabricEthEstcPortMode
    MAX-ACCESS   read-only
    STATUS       current
    DESCRIPTION
        "Cisco UCS fabric:EthEstcEp:portMode managed object property"
    ::= { cucsFabricEthEstcEpEntry 19 }

cucsFabricEthEstcEpPrio OBJECT-TYPE
    SYNTAX       CucsFabricEthEstcEpPrio
    MAX-ACCESS   read-only
    STATUS       current
    DESCRIPTION
        "Cisco UCS fabric:EthEstcEp:prio managed object property"
    ::= { cucsFabricEthEstcEpEntry 20 }

cucsFabricEthEstcEpSlotId OBJECT-TYPE
    SYNTAX       CucsFabricEthEstcEpSlotId
    MAX-ACCESS   read-only
    STATUS       current
    DESCRIPTION
        "Cisco UCS fabric:EthEstcEp:slotId managed object property"
    ::= { cucsFabricEthEstcEpEntry 21 }

cucsFabricEthEstcEpSwitchId OBJECT-TYPE
    SYNTAX       CucsNetworkSwitchId
    MAX-ACCESS   read-only
    STATUS       current
    DESCRIPTION
        "Cisco UCS fabric:EthEstcEp:switchId managed object property"
    ::= { cucsFabricEthEstcEpEntry 22 }

cucsFabricEthEstcEpTransport OBJECT-TYPE
    SYNTAX       CucsFabricEthEstcEpTransport
    MAX-ACCESS   read-only
    STATUS       current
    DESCRIPTION
        "Cisco UCS fabric:EthEstcEp:transport managed object property"
    ::= { cucsFabricEthEstcEpEntry 23 }

cucsFabricEthEstcEpType OBJECT-TYPE
    SYNTAX       CucsFabricEthEstcEpType
    MAX-ACCESS   read-only
    STATUS       current
    DESCRIPTION
        "Cisco UCS fabric:EthEstcEp:type managed object property"
    ::= { cucsFabricEthEstcEpEntry 24 }

cucsFabricEthEstcEpUsrLbl OBJECT-TYPE
    SYNTAX       SnmpAdminString
    MAX-ACCESS   read-only
    STATUS       current
    DESCRIPTION
        "Cisco UCS fabric:EthEstcEp:usrLbl managed object property"
    ::= { cucsFabricEthEstcEpEntry 25 }

cucsFabricEthEstcEpAdminSpeed OBJECT-TYPE
    SYNTAX       CucsPortEthSpeed
    MAX-ACCESS   read-only
    STATUS       current
    DESCRIPTION
        "Cisco UCS fabric:EthEstcEp:adminSpeed managed object property"
    ::= { cucsFabricEthEstcEpEntry 26 }

cucsFabricEthEstcEpPeerChassisId OBJECT-TYPE
    SYNTAX       Gauge32
    MAX-ACCESS   read-only
    STATUS       current
    DESCRIPTION
        "Cisco UCS fabric:EthEstcEp:peerChassisId managed object property"
    ::= { cucsFabricEthEstcEpEntry 27 }

cucsFabricEthEstcEpFltAggr OBJECT-TYPE
    SYNTAX       Unsigned64
    MAX-ACCESS   read-only
    STATUS       current
    DESCRIPTION
        "Cisco UCS fabric:EthEstcEp:fltAggr managed object property"
    ::= { cucsFabricEthEstcEpEntry 28 }

cucsFabricEthEstcEpNwCtrlPolicyName OBJECT-TYPE
    SYNTAX       SnmpAdminString
    MAX-ACCESS   read-only
    STATUS       current
    DESCRIPTION
        "Cisco UCS fabric:EthEstcEp:nwCtrlPolicyName managed
        object property"
    ::= { cucsFabricEthEstcEpEntry 29 }

cucsFabricEthEstcEpOperNwCtrlPolicyName OBJECT-TYPE
    SYNTAX       SnmpAdminString
    MAX-ACCESS   read-only
    STATUS       current
    DESCRIPTION
        "Cisco UCS fabric:EthEstcEp:operNwCtrlPolicyName
        managed object property"
    ::= { cucsFabricEthEstcEpEntry 30 }

cucsFabricEthEstcPcTable OBJECT-TYPE
    SYNTAX           SEQUENCE OF CucsFabricEthEstcPcEntry
    MAX-ACCESS       not-accessible
    STATUS           current
    DESCRIPTION
        "Cisco UCS fabric:EthEstcPc managed object table"
    ::= { cucsFabricObjects 67 }

cucsFabricEthEstcPcEntry OBJECT-TYPE
    SYNTAX           CucsFabricEthEstcPcEntry
    MAX-ACCESS       not-accessible
    STATUS           current
    DESCRIPTION
        "Entry for the cucsFabricEthEstcPcTable table."
    INDEX { cucsFabricEthEstcPcInstanceId }
    ::= { cucsFabricEthEstcPcTable 1 }

CucsFabricEthEstcPcEntry ::= SEQUENCE {
    cucsFabricEthEstcPcInstanceId                                    CucsManagedObjectId,
    cucsFabricEthEstcPcDn                                            CucsManagedObjectDn,
    cucsFabricEthEstcPcRn                                            SnmpAdminString,
    cucsFabricEthEstcPcAdminSpeed                                    CucsPortEthSpeed,
    cucsFabricEthEstcPcAdminState                                    CucsFabricAdminState,
    cucsFabricEthEstcPcEpDn                                          SnmpAdminString,
    cucsFabricEthEstcPcFltAggr                                       Unsigned64,
    cucsFabricEthEstcPcIfRole                                        CucsFabricEstcPcIfRole,
    cucsFabricEthEstcPcIfType                                        CucsFabricCIoEpIfType,
    cucsFabricEthEstcPcLocale                                        CucsFabricExternalPcLocale,
    cucsFabricEthEstcPcName                                          SnmpAdminString,
    cucsFabricEthEstcPcOperSpeed                                     CucsPortEthSpeed,
    cucsFabricEthEstcPcOperState                                     CucsNetworkPortOperState,
    cucsFabricEthEstcPcPeerDn                                        SnmpAdminString,
    cucsFabricEthEstcPcPinGroupName                                  SnmpAdminString,
    cucsFabricEthEstcPcPortId                                        Gauge32,
    cucsFabricEthEstcPcPortMode                                      CucsFabricEthEstcPortMode,
    cucsFabricEthEstcPcPrio                                          CucsQosPriority,
    cucsFabricEthEstcPcStateQual                                     SnmpAdminString,
    cucsFabricEthEstcPcSwitchId                                      CucsNetworkSwitchId,
    cucsFabricEthEstcPcTransport                                     CucsFabricEthEstcPcTransport,
    cucsFabricEthEstcPcType                                          CucsFabricEstcPcType,
    cucsFabricEthEstcPcNwCtrlPolicyName                              SnmpAdminString,
    cucsFabricEthEstcPcOperNwCtrlPolicyName                          SnmpAdminString,
    cucsFabricEthEstcPcProtocol                                      CucsFabricEthPcProtocol
}

cucsFabricEthEstcPcInstanceId OBJECT-TYPE
    SYNTAX       CucsManagedObjectId
    MAX-ACCESS   not-accessible
    STATUS       current
    DESCRIPTION
        "Instance identifier of the managed object."
    ::= { cucsFabricEthEstcPcEntry 1 }

cucsFabricEthEstcPcDn OBJECT-TYPE
    SYNTAX       CucsManagedObjectDn
    MAX-ACCESS   read-only
    STATUS       current
    DESCRIPTION
        "Cisco UCS fabric:EthEstcPc:dn managed object property"
    ::= { cucsFabricEthEstcPcEntry 2 }

cucsFabricEthEstcPcRn OBJECT-TYPE
    SYNTAX       SnmpAdminString
    MAX-ACCESS   read-only
    STATUS       current
    DESCRIPTION
        "Cisco UCS fabric:EthEstcPc:rn managed object property"
    ::= { cucsFabricEthEstcPcEntry 3 }

cucsFabricEthEstcPcAdminSpeed OBJECT-TYPE
    SYNTAX       CucsPortEthSpeed
    MAX-ACCESS   read-only
    STATUS       current
    DESCRIPTION
        "Cisco UCS fabric:EthEstcPc:adminSpeed managed object property"
    ::= { cucsFabricEthEstcPcEntry 4 }

cucsFabricEthEstcPcAdminState OBJECT-TYPE
    SYNTAX       CucsFabricAdminState
    MAX-ACCESS   read-only
    STATUS       current
    DESCRIPTION
        "Cisco UCS fabric:EthEstcPc:adminState managed object property"
    ::= { cucsFabricEthEstcPcEntry 5 }

cucsFabricEthEstcPcEpDn OBJECT-TYPE
    SYNTAX       SnmpAdminString
    MAX-ACCESS   read-only
    STATUS       current
    DESCRIPTION
        "Cisco UCS fabric:EthEstcPc:epDn managed object property"
    ::= { cucsFabricEthEstcPcEntry 6 }

cucsFabricEthEstcPcFltAggr OBJECT-TYPE
    SYNTAX       Unsigned64
    MAX-ACCESS   read-only
    STATUS       current
    DESCRIPTION
        "Cisco UCS fabric:EthEstcPc:fltAggr managed object property"
    ::= { cucsFabricEthEstcPcEntry 7 }

cucsFabricEthEstcPcIfRole OBJECT-TYPE
    SYNTAX       CucsFabricEstcPcIfRole
    MAX-ACCESS   read-only
    STATUS       current
    DESCRIPTION
        "Cisco UCS fabric:EthEstcPc:ifRole managed object property"
    ::= { cucsFabricEthEstcPcEntry 8 }

cucsFabricEthEstcPcIfType OBJECT-TYPE
    SYNTAX       CucsFabricCIoEpIfType
    MAX-ACCESS   read-only
    STATUS       current
    DESCRIPTION
        "Cisco UCS fabric:EthEstcPc:ifType managed object property"
    ::= { cucsFabricEthEstcPcEntry 9 }

cucsFabricEthEstcPcLocale OBJECT-TYPE
    SYNTAX       CucsFabricExternalPcLocale
    MAX-ACCESS   read-only
    STATUS       current
    DESCRIPTION
        "Cisco UCS fabric:EthEstcPc:locale managed object property"
    ::= { cucsFabricEthEstcPcEntry 10 }

cucsFabricEthEstcPcName OBJECT-TYPE
    SYNTAX       SnmpAdminString
    MAX-ACCESS   read-only
    STATUS       current
    DESCRIPTION
        "Cisco UCS fabric:EthEstcPc:name managed object property"
    ::= { cucsFabricEthEstcPcEntry 11 }

cucsFabricEthEstcPcOperSpeed OBJECT-TYPE
    SYNTAX       CucsPortEthSpeed
    MAX-ACCESS   read-only
    STATUS       current
    DESCRIPTION
        "Cisco UCS fabric:EthEstcPc:operSpeed managed object property"
    ::= { cucsFabricEthEstcPcEntry 12 }

cucsFabricEthEstcPcOperState OBJECT-TYPE
    SYNTAX       CucsNetworkPortOperState
    MAX-ACCESS   read-only
    STATUS       current
    DESCRIPTION
        "Cisco UCS fabric:EthEstcPc:operState managed object property"
    ::= { cucsFabricEthEstcPcEntry 13 }

cucsFabricEthEstcPcPeerDn OBJECT-TYPE
    SYNTAX       SnmpAdminString
    MAX-ACCESS   read-only
    STATUS       current
    DESCRIPTION
        "Cisco UCS fabric:EthEstcPc:peerDn managed object property"
    ::= { cucsFabricEthEstcPcEntry 14 }

cucsFabricEthEstcPcPinGroupName OBJECT-TYPE
    SYNTAX       SnmpAdminString
    MAX-ACCESS   read-only
    STATUS       current
    DESCRIPTION
        "Cisco UCS fabric:EthEstcPc:pinGroupName managed object property"
    ::= { cucsFabricEthEstcPcEntry 15 }

cucsFabricEthEstcPcPortId OBJECT-TYPE
    SYNTAX       Gauge32
    MAX-ACCESS   read-only
    STATUS       current
    DESCRIPTION
        "Cisco UCS fabric:EthEstcPc:portId managed object property"
    ::= { cucsFabricEthEstcPcEntry 16 }

cucsFabricEthEstcPcPortMode OBJECT-TYPE
    SYNTAX       CucsFabricEthEstcPortMode
    MAX-ACCESS   read-only
    STATUS       current
    DESCRIPTION
        "Cisco UCS fabric:EthEstcPc:portMode managed object property"
    ::= { cucsFabricEthEstcPcEntry 17 }

cucsFabricEthEstcPcPrio OBJECT-TYPE
    SYNTAX       CucsQosPriority
    MAX-ACCESS   read-only
    STATUS       current
    DESCRIPTION
        "Cisco UCS fabric:EthEstcPc:prio managed object property"
    ::= { cucsFabricEthEstcPcEntry 18 }

cucsFabricEthEstcPcStateQual OBJECT-TYPE
    SYNTAX       SnmpAdminString
    MAX-ACCESS   read-only
    STATUS       current
    DESCRIPTION
        "Cisco UCS fabric:EthEstcPc:stateQual managed object property"
    ::= { cucsFabricEthEstcPcEntry 19 }

cucsFabricEthEstcPcSwitchId OBJECT-TYPE
    SYNTAX       CucsNetworkSwitchId
    MAX-ACCESS   read-only
    STATUS       current
    DESCRIPTION
        "Cisco UCS fabric:EthEstcPc:switchId managed object property"
    ::= { cucsFabricEthEstcPcEntry 20 }

cucsFabricEthEstcPcTransport OBJECT-TYPE
    SYNTAX       CucsFabricEthEstcPcTransport
    MAX-ACCESS   read-only
    STATUS       current
    DESCRIPTION
        "Cisco UCS fabric:EthEstcPc:transport managed object property"
    ::= { cucsFabricEthEstcPcEntry 21 }

cucsFabricEthEstcPcType OBJECT-TYPE
    SYNTAX       CucsFabricEstcPcType
    MAX-ACCESS   read-only
    STATUS       current
    DESCRIPTION
        "Cisco UCS fabric:EthEstcPc:type managed object property"
    ::= { cucsFabricEthEstcPcEntry 22 }

cucsFabricEthEstcPcNwCtrlPolicyName OBJECT-TYPE
    SYNTAX       SnmpAdminString
    MAX-ACCESS   read-only
    STATUS       current
    DESCRIPTION
        "Cisco UCS fabric:EthEstcPc:nwCtrlPolicyName managed
        object property"
    ::= { cucsFabricEthEstcPcEntry 23 }

cucsFabricEthEstcPcOperNwCtrlPolicyName OBJECT-TYPE
    SYNTAX       SnmpAdminString
    MAX-ACCESS   read-only
    STATUS       current
    DESCRIPTION
        "Cisco UCS fabric:EthEstcPc:operNwCtrlPolicyName
        managed object property"
    ::= { cucsFabricEthEstcPcEntry 24 }

cucsFabricEthEstcPcProtocol OBJECT-TYPE
    SYNTAX       CucsFabricEthPcProtocol
    MAX-ACCESS   read-only
    STATUS       current
    DESCRIPTION
        "Cisco UCS fabric:EthEstcPc:protocol managed object property"
    ::= { cucsFabricEthEstcPcEntry 25 }

cucsFabricEthEstcPcEpTable OBJECT-TYPE
    SYNTAX           SEQUENCE OF CucsFabricEthEstcPcEpEntry
    MAX-ACCESS       not-accessible
    STATUS           current
    DESCRIPTION
        "Cisco UCS fabric:EthEstcPcEp managed object table"
    ::= { cucsFabricObjects 68 }

cucsFabricEthEstcPcEpEntry OBJECT-TYPE
    SYNTAX           CucsFabricEthEstcPcEpEntry
    MAX-ACCESS       not-accessible
    STATUS           current
    DESCRIPTION
        "Entry for the cucsFabricEthEstcPcEpTable table."
    INDEX { cucsFabricEthEstcPcEpInstanceId }
    ::= { cucsFabricEthEstcPcEpTable 1 }

CucsFabricEthEstcPcEpEntry ::= SEQUENCE {
    cucsFabricEthEstcPcEpInstanceId                                  CucsManagedObjectId,
    cucsFabricEthEstcPcEpDn                                          CucsManagedObjectDn,
    cucsFabricEthEstcPcEpRn                                          SnmpAdminString,
    cucsFabricEthEstcPcEpAdminSpeed                                  CucsPortSpeed,
    cucsFabricEthEstcPcEpAdminState                                  CucsFabricExternalEpAdminState,
    cucsFabricEthEstcPcEpChassisId                                   Gauge32,
    cucsFabricEthEstcPcEpConfigState                                 CucsFabricConfigState,
    cucsFabricEthEstcPcEpEpDn                                        SnmpAdminString,
    cucsFabricEthEstcPcEpIfRole                                      CucsFabricAEthEstcEpIfRole,
    cucsFabricEthEstcPcEpIfType                                      CucsFabricPIoEpIfType,
    cucsFabricEthEstcPcEpLicGP                                       Unsigned64,
    cucsFabricEthEstcPcEpLicState                                    CucsLicenseState,
    cucsFabricEthEstcPcEpLocale                                      CucsFabricExternalEpLocale,
    cucsFabricEthEstcPcEpMembership                                  CucsFabricMembershipStatus,
    cucsFabricEthEstcPcEpName                                        SnmpAdminString,
    cucsFabricEthEstcPcEpPeerChassisId                               Gauge32,
    cucsFabricEthEstcPcEpPeerDn                                      SnmpAdminString,
    cucsFabricEthEstcPcEpPeerPortId                                  Gauge32,
    cucsFabricEthEstcPcEpPeerSlotId                                  Gauge32,
    cucsFabricEthEstcPcEpPortId                                      CucsFabricEthEstcPcEpPortId,
    cucsFabricEthEstcPcEpSlotId                                      CucsFabricEthEstcPcEpSlotId,
    cucsFabricEthEstcPcEpSwitchId                                    CucsNetworkSwitchId,
    cucsFabricEthEstcPcEpTransport                                   CucsFabricAEthEstcEpTransport,
    cucsFabricEthEstcPcEpType                                        CucsFabricAEthEstcEpType,
    cucsFabricEthEstcPcEpUsrLbl                                      SnmpAdminString,
    cucsFabricEthEstcPcEpFltAggr                                     Unsigned64
}

cucsFabricEthEstcPcEpInstanceId OBJECT-TYPE
    SYNTAX       CucsManagedObjectId
    MAX-ACCESS   not-accessible
    STATUS       current
    DESCRIPTION
        "Instance identifier of the managed object."
    ::= { cucsFabricEthEstcPcEpEntry 1 }

cucsFabricEthEstcPcEpDn OBJECT-TYPE
    SYNTAX       CucsManagedObjectDn
    MAX-ACCESS   read-only
    STATUS       current
    DESCRIPTION
        "Cisco UCS fabric:EthEstcPcEp:dn managed object property"
    ::= { cucsFabricEthEstcPcEpEntry 2 }

cucsFabricEthEstcPcEpRn OBJECT-TYPE
    SYNTAX       SnmpAdminString
    MAX-ACCESS   read-only
    STATUS       current
    DESCRIPTION
        "Cisco UCS fabric:EthEstcPcEp:rn managed object property"
    ::= { cucsFabricEthEstcPcEpEntry 3 }

cucsFabricEthEstcPcEpAdminSpeed OBJECT-TYPE
    SYNTAX       CucsPortSpeed
    MAX-ACCESS   read-only
    STATUS       current
    DESCRIPTION
        "Cisco UCS fabric:EthEstcPcEp:adminSpeed managed object property"
    ::= { cucsFabricEthEstcPcEpEntry 4 }

cucsFabricEthEstcPcEpAdminState OBJECT-TYPE
    SYNTAX       CucsFabricExternalEpAdminState
    MAX-ACCESS   read-only
    STATUS       current
    DESCRIPTION
        "Cisco UCS fabric:EthEstcPcEp:adminState managed object property"
    ::= { cucsFabricEthEstcPcEpEntry 5 }

cucsFabricEthEstcPcEpChassisId OBJECT-TYPE
    SYNTAX       Gauge32
    MAX-ACCESS   read-only
    STATUS       current
    DESCRIPTION
        "Cisco UCS fabric:EthEstcPcEp:chassisId managed object property"
    ::= { cucsFabricEthEstcPcEpEntry 6 }

cucsFabricEthEstcPcEpConfigState OBJECT-TYPE
    SYNTAX       CucsFabricConfigState
    MAX-ACCESS   read-only
    STATUS       current
    DESCRIPTION
        "Cisco UCS fabric:EthEstcPcEp:configState managed object property"
    ::= { cucsFabricEthEstcPcEpEntry 7 }

cucsFabricEthEstcPcEpEpDn OBJECT-TYPE
    SYNTAX       SnmpAdminString
    MAX-ACCESS   read-only
    STATUS       current
    DESCRIPTION
        "Cisco UCS fabric:EthEstcPcEp:epDn managed object property"
    ::= { cucsFabricEthEstcPcEpEntry 8 }

cucsFabricEthEstcPcEpIfRole OBJECT-TYPE
    SYNTAX       CucsFabricAEthEstcEpIfRole
    MAX-ACCESS   read-only
    STATUS       current
    DESCRIPTION
        "Cisco UCS fabric:EthEstcPcEp:ifRole managed object property"
    ::= { cucsFabricEthEstcPcEpEntry 9 }

cucsFabricEthEstcPcEpIfType OBJECT-TYPE
    SYNTAX       CucsFabricPIoEpIfType
    MAX-ACCESS   read-only
    STATUS       current
    DESCRIPTION
        "Cisco UCS fabric:EthEstcPcEp:ifType managed object property"
    ::= { cucsFabricEthEstcPcEpEntry 10 }

cucsFabricEthEstcPcEpLicGP OBJECT-TYPE
    SYNTAX       Unsigned64
    MAX-ACCESS   read-only
    STATUS       current
    DESCRIPTION
        "Cisco UCS fabric:EthEstcPcEp:licGP managed object property"
    ::= { cucsFabricEthEstcPcEpEntry 11 }

cucsFabricEthEstcPcEpLicState OBJECT-TYPE
    SYNTAX       CucsLicenseState
    MAX-ACCESS   read-only
    STATUS       current
    DESCRIPTION
        "Cisco UCS fabric:EthEstcPcEp:licState managed object property"
    ::= { cucsFabricEthEstcPcEpEntry 12 }

cucsFabricEthEstcPcEpLocale OBJECT-TYPE
    SYNTAX       CucsFabricExternalEpLocale
    MAX-ACCESS   read-only
    STATUS       current
    DESCRIPTION
        "Cisco UCS fabric:EthEstcPcEp:locale managed object property"
    ::= { cucsFabricEthEstcPcEpEntry 13 }

cucsFabricEthEstcPcEpMembership OBJECT-TYPE
    SYNTAX       CucsFabricMembershipStatus
    MAX-ACCESS   read-only
    STATUS       current
    DESCRIPTION
        "Cisco UCS fabric:EthEstcPcEp:membership managed object property"
    ::= { cucsFabricEthEstcPcEpEntry 14 }

cucsFabricEthEstcPcEpName OBJECT-TYPE
    SYNTAX       SnmpAdminString
    MAX-ACCESS   read-only
    STATUS       current
    DESCRIPTION
        "Cisco UCS fabric:EthEstcPcEp:name managed object property"
    ::= { cucsFabricEthEstcPcEpEntry 15 }

cucsFabricEthEstcPcEpPeerChassisId OBJECT-TYPE
    SYNTAX       Gauge32
    MAX-ACCESS   read-only
    STATUS       current
    DESCRIPTION
        "Cisco UCS fabric:EthEstcPcEp:peerChassisId managed
        object property"
    ::= { cucsFabricEthEstcPcEpEntry 16 }

cucsFabricEthEstcPcEpPeerDn OBJECT-TYPE
    SYNTAX       SnmpAdminString
    MAX-ACCESS   read-only
    STATUS       current
    DESCRIPTION
        "Cisco UCS fabric:EthEstcPcEp:peerDn managed object property"
    ::= { cucsFabricEthEstcPcEpEntry 17 }

cucsFabricEthEstcPcEpPeerPortId OBJECT-TYPE
    SYNTAX       Gauge32
    MAX-ACCESS   read-only
    STATUS       current
    DESCRIPTION
        "Cisco UCS fabric:EthEstcPcEp:peerPortId managed object property"
    ::= { cucsFabricEthEstcPcEpEntry 18 }

cucsFabricEthEstcPcEpPeerSlotId OBJECT-TYPE
    SYNTAX       Gauge32
    MAX-ACCESS   read-only
    STATUS       current
    DESCRIPTION
        "Cisco UCS fabric:EthEstcPcEp:peerSlotId managed object property"
    ::= { cucsFabricEthEstcPcEpEntry 19 }

cucsFabricEthEstcPcEpPortId OBJECT-TYPE
    SYNTAX       CucsFabricEthEstcPcEpPortId
    MAX-ACCESS   read-only
    STATUS       current
    DESCRIPTION
        "Cisco UCS fabric:EthEstcPcEp:portId managed object property"
    ::= { cucsFabricEthEstcPcEpEntry 20 }

cucsFabricEthEstcPcEpSlotId OBJECT-TYPE
    SYNTAX       CucsFabricEthEstcPcEpSlotId
    MAX-ACCESS   read-only
    STATUS       current
    DESCRIPTION
        "Cisco UCS fabric:EthEstcPcEp:slotId managed object property"
    ::= { cucsFabricEthEstcPcEpEntry 21 }

cucsFabricEthEstcPcEpSwitchId OBJECT-TYPE
    SYNTAX       CucsNetworkSwitchId
    MAX-ACCESS   read-only
    STATUS       current
    DESCRIPTION
        "Cisco UCS fabric:EthEstcPcEp:switchId managed object property"
    ::= { cucsFabricEthEstcPcEpEntry 22 }

cucsFabricEthEstcPcEpTransport OBJECT-TYPE
    SYNTAX       CucsFabricAEthEstcEpTransport
    MAX-ACCESS   read-only
    STATUS       current
    DESCRIPTION
        "Cisco UCS fabric:EthEstcPcEp:transport managed object property"
    ::= { cucsFabricEthEstcPcEpEntry 23 }

cucsFabricEthEstcPcEpType OBJECT-TYPE
    SYNTAX       CucsFabricAEthEstcEpType
    MAX-ACCESS   read-only
    STATUS       current
    DESCRIPTION
        "Cisco UCS fabric:EthEstcPcEp:type managed object property"
    ::= { cucsFabricEthEstcPcEpEntry 24 }

cucsFabricEthEstcPcEpUsrLbl OBJECT-TYPE
    SYNTAX       SnmpAdminString
    MAX-ACCESS   read-only
    STATUS       current
    DESCRIPTION
        "Cisco UCS fabric:EthEstcPcEp:usrLbl managed object property"
    ::= { cucsFabricEthEstcPcEpEntry 25 }

cucsFabricEthEstcPcEpFltAggr OBJECT-TYPE
    SYNTAX       Unsigned64
    MAX-ACCESS   read-only
    STATUS       current
    DESCRIPTION
        "Cisco UCS fabric:EthEstcPcEp:fltAggr managed object property"
    ::= { cucsFabricEthEstcPcEpEntry 26 }

cucsFabricEthLanTable OBJECT-TYPE
    SYNTAX           SEQUENCE OF CucsFabricEthLanEntry
    MAX-ACCESS       not-accessible
    STATUS           current
    DESCRIPTION
        "Cisco UCS fabric:EthLan managed object table"
    ::= { cucsFabricObjects 12 }

cucsFabricEthLanEntry OBJECT-TYPE
    SYNTAX           CucsFabricEthLanEntry
    MAX-ACCESS       not-accessible
    STATUS           current
    DESCRIPTION
        "Entry for the cucsFabricEthLanTable table."
    INDEX { cucsFabricEthLanInstanceId }
    ::= { cucsFabricEthLanTable 1 }

CucsFabricEthLanEntry ::= SEQUENCE {
    cucsFabricEthLanInstanceId                                       CucsManagedObjectId,
    cucsFabricEthLanDn                                               CucsManagedObjectDn,
    cucsFabricEthLanRn                                               SnmpAdminString,
    cucsFabricEthLanId                                               CucsNetworkSwitchId,
    cucsFabricEthLanLocale                                           CucsFabricExternalLocale,
    cucsFabricEthLanName                                             SnmpAdminString,
    cucsFabricEthLanTransport                                        CucsFabricEthLanTransport,
    cucsFabricEthLanType                                             CucsFabricLanType
}

cucsFabricEthLanInstanceId OBJECT-TYPE
    SYNTAX       CucsManagedObjectId
    MAX-ACCESS   not-accessible
    STATUS       current
    DESCRIPTION
        "Instance identifier of the managed object."
    ::= { cucsFabricEthLanEntry 1 }

cucsFabricEthLanDn OBJECT-TYPE
    SYNTAX       CucsManagedObjectDn
    MAX-ACCESS   read-only
    STATUS       current
    DESCRIPTION
        "Cisco UCS fabric:EthLan:dn managed object property"
    ::= { cucsFabricEthLanEntry 2 }

cucsFabricEthLanRn OBJECT-TYPE
    SYNTAX       SnmpAdminString
    MAX-ACCESS   read-only
    STATUS       current
    DESCRIPTION
        "Cisco UCS fabric:EthLan:rn managed object property"
    ::= { cucsFabricEthLanEntry 3 }

cucsFabricEthLanId OBJECT-TYPE
    SYNTAX       CucsNetworkSwitchId
    MAX-ACCESS   read-only
    STATUS       current
    DESCRIPTION
        "Cisco UCS fabric:EthLan:id managed object property"
    ::= { cucsFabricEthLanEntry 4 }

cucsFabricEthLanLocale OBJECT-TYPE
    SYNTAX       CucsFabricExternalLocale
    MAX-ACCESS   read-only
    STATUS       current
    DESCRIPTION
        "Cisco UCS fabric:EthLan:locale managed object property"
    ::= { cucsFabricEthLanEntry 5 }

cucsFabricEthLanName OBJECT-TYPE
    SYNTAX       SnmpAdminString
    MAX-ACCESS   read-only
    STATUS       current
    DESCRIPTION
        "Cisco UCS fabric:EthLan:name managed object property"
    ::= { cucsFabricEthLanEntry 6 }

cucsFabricEthLanTransport OBJECT-TYPE
    SYNTAX       CucsFabricEthLanTransport
    MAX-ACCESS   read-only
    STATUS       current
    DESCRIPTION
        "Cisco UCS fabric:EthLan:transport managed object property"
    ::= { cucsFabricEthLanEntry 7 }

cucsFabricEthLanType OBJECT-TYPE
    SYNTAX       CucsFabricLanType
    MAX-ACCESS   read-only
    STATUS       current
    DESCRIPTION
        "Cisco UCS fabric:EthLan:type managed object property"
    ::= { cucsFabricEthLanEntry 8 }

cucsFabricEthLanEpTable OBJECT-TYPE
    SYNTAX           SEQUENCE OF CucsFabricEthLanEpEntry
    MAX-ACCESS       not-accessible
    STATUS           current
    DESCRIPTION
        "Cisco UCS fabric:EthLanEp managed object table"
    ::= { cucsFabricObjects 13 }

cucsFabricEthLanEpEntry OBJECT-TYPE
    SYNTAX           CucsFabricEthLanEpEntry
    MAX-ACCESS       not-accessible
    STATUS           current
    DESCRIPTION
        "Entry for the cucsFabricEthLanEpTable table."
    INDEX { cucsFabricEthLanEpInstanceId }
    ::= { cucsFabricEthLanEpTable 1 }

CucsFabricEthLanEpEntry ::= SEQUENCE {
    cucsFabricEthLanEpInstanceId                                     CucsManagedObjectId,
    cucsFabricEthLanEpDn                                             CucsManagedObjectDn,
    cucsFabricEthLanEpRn                                             SnmpAdminString,
    cucsFabricEthLanEpAdminSpeed                                     CucsPortEthSpeed,
    cucsFabricEthLanEpAdminState                                     CucsFabricExternalEpAdminState,
    cucsFabricEthLanEpChassisId                                      Gauge32,
    cucsFabricEthLanEpEpDn                                           SnmpAdminString,
    cucsFabricEthLanEpFlowCtrlPolicy                                 SnmpAdminString,
    cucsFabricEthLanEpIfRole                                         CucsFabricLanEpIfRole,
    cucsFabricEthLanEpIfType                                         CucsFabricPIoEpIfType,
    cucsFabricEthLanEpLicGP                                          Unsigned64,
    cucsFabricEthLanEpLicState                                       CucsLicenseState,
    cucsFabricEthLanEpLocale                                         CucsFabricExternalEpLocale,
    cucsFabricEthLanEpName                                           SnmpAdminString,
    cucsFabricEthLanEpPeerDn                                         SnmpAdminString,
    cucsFabricEthLanEpPeerPortId                                     Gauge32,
    cucsFabricEthLanEpPeerSlotId                                     Gauge32,
    cucsFabricEthLanEpPortId                                         Gauge32,
    cucsFabricEthLanEpSlotId                                         Gauge32,
    cucsFabricEthLanEpSwitchId                                       CucsNetworkSwitchId,
    cucsFabricEthLanEpTransport                                      CucsFabricAEthLanEpTransport,
    cucsFabricEthLanEpType                                           CucsFabricLanEpType,
    cucsFabricEthLanEpUsrLbl                                         SnmpAdminString,
    cucsFabricEthLanEpPeerChassisId                                  Gauge32,
    cucsFabricEthLanEpFltAggr                                        Unsigned64
}

cucsFabricEthLanEpInstanceId OBJECT-TYPE
    SYNTAX       CucsManagedObjectId
    MAX-ACCESS   not-accessible
    STATUS       current
    DESCRIPTION
        "Instance identifier of the managed object."
    ::= { cucsFabricEthLanEpEntry 1 }

cucsFabricEthLanEpDn OBJECT-TYPE
    SYNTAX       CucsManagedObjectDn
    MAX-ACCESS   read-only
    STATUS       current
    DESCRIPTION
        "Cisco UCS fabric:EthLanEp:dn managed object property"
    ::= { cucsFabricEthLanEpEntry 2 }

cucsFabricEthLanEpRn OBJECT-TYPE
    SYNTAX       SnmpAdminString
    MAX-ACCESS   read-only
    STATUS       current
    DESCRIPTION
        "Cisco UCS fabric:EthLanEp:rn managed object property"
    ::= { cucsFabricEthLanEpEntry 3 }

cucsFabricEthLanEpAdminSpeed OBJECT-TYPE
    SYNTAX       CucsPortEthSpeed
    MAX-ACCESS   read-only
    STATUS       current
    DESCRIPTION
        "Cisco UCS fabric:EthLanEp:adminSpeed managed object property"
    ::= { cucsFabricEthLanEpEntry 4 }

cucsFabricEthLanEpAdminState OBJECT-TYPE
    SYNTAX       CucsFabricExternalEpAdminState
    MAX-ACCESS   read-only
    STATUS       current
    DESCRIPTION
        "Cisco UCS fabric:EthLanEp:adminState managed object property"
    ::= { cucsFabricEthLanEpEntry 5 }

cucsFabricEthLanEpChassisId OBJECT-TYPE
    SYNTAX       Gauge32
    MAX-ACCESS   read-only
    STATUS       current
    DESCRIPTION
        "Cisco UCS fabric:EthLanEp:chassisId managed object property"
    ::= { cucsFabricEthLanEpEntry 6 }

cucsFabricEthLanEpEpDn OBJECT-TYPE
    SYNTAX       SnmpAdminString
    MAX-ACCESS   read-only
    STATUS       current
    DESCRIPTION
        "Cisco UCS fabric:EthLanEp:epDn managed object property"
    ::= { cucsFabricEthLanEpEntry 7 }

cucsFabricEthLanEpFlowCtrlPolicy OBJECT-TYPE
    SYNTAX       SnmpAdminString
    MAX-ACCESS   read-only
    STATUS       current
    DESCRIPTION
        "Cisco UCS fabric:EthLanEp:flowCtrlPolicy managed object property"
    ::= { cucsFabricEthLanEpEntry 8 }

cucsFabricEthLanEpIfRole OBJECT-TYPE
    SYNTAX       CucsFabricLanEpIfRole
    MAX-ACCESS   read-only
    STATUS       current
    DESCRIPTION
        "Cisco UCS fabric:EthLanEp:ifRole managed object property"
    ::= { cucsFabricEthLanEpEntry 9 }

cucsFabricEthLanEpIfType OBJECT-TYPE
    SYNTAX       CucsFabricPIoEpIfType
    MAX-ACCESS   read-only
    STATUS       current
    DESCRIPTION
        "Cisco UCS fabric:EthLanEp:ifType managed object property"
    ::= { cucsFabricEthLanEpEntry 10 }

cucsFabricEthLanEpLicGP OBJECT-TYPE
    SYNTAX       Unsigned64
    MAX-ACCESS   read-only
    STATUS       current
    DESCRIPTION
        "Cisco UCS fabric:EthLanEp:licGP managed object property"
    ::= { cucsFabricEthLanEpEntry 11 }

cucsFabricEthLanEpLicState OBJECT-TYPE
    SYNTAX       CucsLicenseState
    MAX-ACCESS   read-only
    STATUS       current
    DESCRIPTION
        "Cisco UCS fabric:EthLanEp:licState managed object property"
    ::= { cucsFabricEthLanEpEntry 12 }

cucsFabricEthLanEpLocale OBJECT-TYPE
    SYNTAX       CucsFabricExternalEpLocale
    MAX-ACCESS   read-only
    STATUS       current
    DESCRIPTION
        "Cisco UCS fabric:EthLanEp:locale managed object property"
    ::= { cucsFabricEthLanEpEntry 13 }

cucsFabricEthLanEpName OBJECT-TYPE
    SYNTAX       SnmpAdminString
    MAX-ACCESS   read-only
    STATUS       current
    DESCRIPTION
        "Cisco UCS fabric:EthLanEp:name managed object property"
    ::= { cucsFabricEthLanEpEntry 14 }

cucsFabricEthLanEpPeerDn OBJECT-TYPE
    SYNTAX       SnmpAdminString
    MAX-ACCESS   read-only
    STATUS       current
    DESCRIPTION
        "Cisco UCS fabric:EthLanEp:peerDn managed object property"
    ::= { cucsFabricEthLanEpEntry 15 }

cucsFabricEthLanEpPeerPortId OBJECT-TYPE
    SYNTAX       Gauge32
    MAX-ACCESS   read-only
    STATUS       current
    DESCRIPTION
        "Cisco UCS fabric:EthLanEp:peerPortId managed object property"
    ::= { cucsFabricEthLanEpEntry 16 }

cucsFabricEthLanEpPeerSlotId OBJECT-TYPE
    SYNTAX       Gauge32
    MAX-ACCESS   read-only
    STATUS       current
    DESCRIPTION
        "Cisco UCS fabric:EthLanEp:peerSlotId managed object property"
    ::= { cucsFabricEthLanEpEntry 17 }

cucsFabricEthLanEpPortId OBJECT-TYPE
    SYNTAX       Gauge32
    MAX-ACCESS   read-only
    STATUS       current
    DESCRIPTION
        "Cisco UCS fabric:EthLanEp:portId managed object property"
    ::= { cucsFabricEthLanEpEntry 18 }

cucsFabricEthLanEpSlotId OBJECT-TYPE
    SYNTAX       Gauge32
    MAX-ACCESS   read-only
    STATUS       current
    DESCRIPTION
        "Cisco UCS fabric:EthLanEp:slotId managed object property"
    ::= { cucsFabricEthLanEpEntry 19 }

cucsFabricEthLanEpSwitchId OBJECT-TYPE
    SYNTAX       CucsNetworkSwitchId
    MAX-ACCESS   read-only
    STATUS       current
    DESCRIPTION
        "Cisco UCS fabric:EthLanEp:switchId managed object property"
    ::= { cucsFabricEthLanEpEntry 20 }

cucsFabricEthLanEpTransport OBJECT-TYPE
    SYNTAX       CucsFabricAEthLanEpTransport
    MAX-ACCESS   read-only
    STATUS       current
    DESCRIPTION
        "Cisco UCS fabric:EthLanEp:transport managed object property"
    ::= { cucsFabricEthLanEpEntry 21 }

cucsFabricEthLanEpType OBJECT-TYPE
    SYNTAX       CucsFabricLanEpType
    MAX-ACCESS   read-only
    STATUS       current
    DESCRIPTION
        "Cisco UCS fabric:EthLanEp:type managed object property"
    ::= { cucsFabricEthLanEpEntry 22 }

cucsFabricEthLanEpUsrLbl OBJECT-TYPE
    SYNTAX       SnmpAdminString
    MAX-ACCESS   read-only
    STATUS       current
    DESCRIPTION
        "Cisco UCS fabric:EthLanEp:usrLbl managed object property"
    ::= { cucsFabricEthLanEpEntry 23 }

cucsFabricEthLanEpPeerChassisId OBJECT-TYPE
    SYNTAX       Gauge32
    MAX-ACCESS   read-only
    STATUS       current
    DESCRIPTION
        "Cisco UCS fabric:EthLanEp:peerChassisId managed object property"
    ::= { cucsFabricEthLanEpEntry 24 }

cucsFabricEthLanEpFltAggr OBJECT-TYPE
    SYNTAX       Unsigned64
    MAX-ACCESS   read-only
    STATUS       current
    DESCRIPTION
        "Cisco UCS fabric:EthLanEp:fltAggr managed object property"
    ::= { cucsFabricEthLanEpEntry 25 }

cucsFabricEthLanPcTable OBJECT-TYPE
    SYNTAX           SEQUENCE OF CucsFabricEthLanPcEntry
    MAX-ACCESS       not-accessible
    STATUS           current
    DESCRIPTION
        "Cisco UCS fabric:EthLanPc managed object table"
    ::= { cucsFabricObjects 14 }

cucsFabricEthLanPcEntry OBJECT-TYPE
    SYNTAX           CucsFabricEthLanPcEntry
    MAX-ACCESS       not-accessible
    STATUS           current
    DESCRIPTION
        "Entry for the cucsFabricEthLanPcTable table."
    INDEX { cucsFabricEthLanPcInstanceId }
    ::= { cucsFabricEthLanPcTable 1 }

CucsFabricEthLanPcEntry ::= SEQUENCE {
    cucsFabricEthLanPcInstanceId                                     CucsManagedObjectId,
    cucsFabricEthLanPcDn                                             CucsManagedObjectDn,
    cucsFabricEthLanPcRn                                             SnmpAdminString,
    cucsFabricEthLanPcAdminSpeed                                     CucsPortEthSpeed,
    cucsFabricEthLanPcAdminState                                     CucsFabricAdminState,
    cucsFabricEthLanPcEndPtDn                                        SnmpAdminString,
    cucsFabricEthLanPcFlowCtrlPolicy                                 SnmpAdminString,
    cucsFabricEthLanPcFltAggr                                        Unsigned64,
    cucsFabricEthLanPcIfRole                                         CucsFabricLanPcIfRole,
    cucsFabricEthLanPcIfType                                         CucsFabricCIoEpIfType,
    cucsFabricEthLanPcLocale                                         CucsFabricExternalPcLocale,
    cucsFabricEthLanPcName                                           SnmpAdminString,
    cucsFabricEthLanPcOperSpeed                                      CucsPortEthSpeed,
    cucsFabricEthLanPcOperState                                      CucsNetworkPortOperState,
    cucsFabricEthLanPcPeerDn                                         SnmpAdminString,
    cucsFabricEthLanPcPortId                                         Gauge32,
    cucsFabricEthLanPcStateQual                                      SnmpAdminString,
    cucsFabricEthLanPcSwitchId                                       CucsNetworkSwitchId,
    cucsFabricEthLanPcTransport                                      CucsFabricEthLanPcTransport,
    cucsFabricEthLanPcType                                           CucsFabricLanPcType
}

cucsFabricEthLanPcInstanceId OBJECT-TYPE
    SYNTAX       CucsManagedObjectId
    MAX-ACCESS   not-accessible
    STATUS       current
    DESCRIPTION
        "Instance identifier of the managed object."
    ::= { cucsFabricEthLanPcEntry 1 }

cucsFabricEthLanPcDn OBJECT-TYPE
    SYNTAX       CucsManagedObjectDn
    MAX-ACCESS   read-only
    STATUS       current
    DESCRIPTION
        "Cisco UCS fabric:EthLanPc:dn managed object property"
    ::= { cucsFabricEthLanPcEntry 2 }

cucsFabricEthLanPcRn OBJECT-TYPE
    SYNTAX       SnmpAdminString
    MAX-ACCESS   read-only
    STATUS       current
    DESCRIPTION
        "Cisco UCS fabric:EthLanPc:rn managed object property"
    ::= { cucsFabricEthLanPcEntry 3 }

cucsFabricEthLanPcAdminSpeed OBJECT-TYPE
    SYNTAX       CucsPortEthSpeed
    MAX-ACCESS   read-only
    STATUS       current
    DESCRIPTION
        "Cisco UCS fabric:EthLanPc:adminSpeed managed object property"
    ::= { cucsFabricEthLanPcEntry 4 }

cucsFabricEthLanPcAdminState OBJECT-TYPE
    SYNTAX       CucsFabricAdminState
    MAX-ACCESS   read-only
    STATUS       current
    DESCRIPTION
        "Cisco UCS fabric:EthLanPc:adminState managed object property"
    ::= { cucsFabricEthLanPcEntry 5 }

cucsFabricEthLanPcEndPtDn OBJECT-TYPE
    SYNTAX       SnmpAdminString
    MAX-ACCESS   read-only
    STATUS       current
    DESCRIPTION
        "Cisco UCS fabric:EthLanPc:epDn managed object property"
    ::= { cucsFabricEthLanPcEntry 6 }

cucsFabricEthLanPcFlowCtrlPolicy OBJECT-TYPE
    SYNTAX       SnmpAdminString
    MAX-ACCESS   read-only
    STATUS       current
    DESCRIPTION
        "Cisco UCS fabric:EthLanPc:flowCtrlPolicy managed object property"
    ::= { cucsFabricEthLanPcEntry 7 }

cucsFabricEthLanPcFltAggr OBJECT-TYPE
    SYNTAX       Unsigned64
    MAX-ACCESS   read-only
    STATUS       current
    DESCRIPTION
        "Cisco UCS fabric:EthLanPc:fltAggr managed object property"
    ::= { cucsFabricEthLanPcEntry 8 }

cucsFabricEthLanPcIfRole OBJECT-TYPE
    SYNTAX       CucsFabricLanPcIfRole
    MAX-ACCESS   read-only
    STATUS       current
    DESCRIPTION
        "Cisco UCS fabric:EthLanPc:ifRole managed object property"
    ::= { cucsFabricEthLanPcEntry 9 }

cucsFabricEthLanPcIfType OBJECT-TYPE
    SYNTAX       CucsFabricCIoEpIfType
    MAX-ACCESS   read-only
    STATUS       current
    DESCRIPTION
        "Cisco UCS fabric:EthLanPc:ifType managed object property"
    ::= { cucsFabricEthLanPcEntry 10 }

cucsFabricEthLanPcLocale OBJECT-TYPE
    SYNTAX       CucsFabricExternalPcLocale
    MAX-ACCESS   read-only
    STATUS       current
    DESCRIPTION
        "Cisco UCS fabric:EthLanPc:locale managed object property"
    ::= { cucsFabricEthLanPcEntry 11 }

cucsFabricEthLanPcName OBJECT-TYPE
    SYNTAX       SnmpAdminString
    MAX-ACCESS   read-only
    STATUS       current
    DESCRIPTION
        "Cisco UCS fabric:EthLanPc:name managed object property"
    ::= { cucsFabricEthLanPcEntry 12 }

cucsFabricEthLanPcOperSpeed OBJECT-TYPE
    SYNTAX       CucsPortEthSpeed
    MAX-ACCESS   read-only
    STATUS       current
    DESCRIPTION
        "Cisco UCS fabric:EthLanPc:operSpeed managed object property"
    ::= { cucsFabricEthLanPcEntry 13 }

cucsFabricEthLanPcOperState OBJECT-TYPE
    SYNTAX       CucsNetworkPortOperState
    MAX-ACCESS   read-only
    STATUS       current
    DESCRIPTION
        "Cisco UCS fabric:EthLanPc:operState managed object property"
    ::= { cucsFabricEthLanPcEntry 14 }

cucsFabricEthLanPcPeerDn OBJECT-TYPE
    SYNTAX       SnmpAdminString
    MAX-ACCESS   read-only
    STATUS       current
    DESCRIPTION
        "Cisco UCS fabric:EthLanPc:peerDn managed object property"
    ::= { cucsFabricEthLanPcEntry 15 }

cucsFabricEthLanPcPortId OBJECT-TYPE
    SYNTAX       Gauge32
    MAX-ACCESS   read-only
    STATUS       current
    DESCRIPTION
        "Cisco UCS fabric:EthLanPc:portId managed object property"
    ::= { cucsFabricEthLanPcEntry 16 }

cucsFabricEthLanPcStateQual OBJECT-TYPE
    SYNTAX       SnmpAdminString
    MAX-ACCESS   read-only
    STATUS       current
    DESCRIPTION
        "Cisco UCS fabric:EthLanPc:stateQual managed object property"
    ::= { cucsFabricEthLanPcEntry 17 }

cucsFabricEthLanPcSwitchId OBJECT-TYPE
    SYNTAX       CucsNetworkSwitchId
    MAX-ACCESS   read-only
    STATUS       current
    DESCRIPTION
        "Cisco UCS fabric:EthLanPc:switchId managed object property"
    ::= { cucsFabricEthLanPcEntry 18 }

cucsFabricEthLanPcTransport OBJECT-TYPE
    SYNTAX       CucsFabricEthLanPcTransport
    MAX-ACCESS   read-only
    STATUS       current
    DESCRIPTION
        "Cisco UCS fabric:EthLanPc:transport managed object property"
    ::= { cucsFabricEthLanPcEntry 19 }

cucsFabricEthLanPcType OBJECT-TYPE
    SYNTAX       CucsFabricLanPcType
    MAX-ACCESS   read-only
    STATUS       current
    DESCRIPTION
        "Cisco UCS fabric:EthLanPc:type managed object property"
    ::= { cucsFabricEthLanPcEntry 20 }

cucsFabricEthLanPcEpTable OBJECT-TYPE
    SYNTAX           SEQUENCE OF CucsFabricEthLanPcEpEntry
    MAX-ACCESS       not-accessible
    STATUS           current
    DESCRIPTION
        "Cisco UCS fabric:EthLanPcEp managed object table"
    ::= { cucsFabricObjects 15 }

cucsFabricEthLanPcEpEntry OBJECT-TYPE
    SYNTAX           CucsFabricEthLanPcEpEntry
    MAX-ACCESS       not-accessible
    STATUS           current
    DESCRIPTION
        "Entry for the cucsFabricEthLanPcEpTable table."
    INDEX { cucsFabricEthLanPcEpInstanceId }
    ::= { cucsFabricEthLanPcEpTable 1 }

CucsFabricEthLanPcEpEntry ::= SEQUENCE {
    cucsFabricEthLanPcEpInstanceId                                   CucsManagedObjectId,
    cucsFabricEthLanPcEpDn                                           CucsManagedObjectDn,
    cucsFabricEthLanPcEpRn                                           SnmpAdminString,
    cucsFabricEthLanPcEpAdminState                                   CucsFabricExternalEpAdminState,
    cucsFabricEthLanPcEpChassisId                                    Gauge32,
    cucsFabricEthLanPcEpEpDn                                         SnmpAdminString,
    cucsFabricEthLanPcEpIfRole                                       CucsFabricLanEpIfRole,
    cucsFabricEthLanPcEpIfType                                       CucsFabricPIoEpIfType,
    cucsFabricEthLanPcEpLicGP                                        Unsigned64,
    cucsFabricEthLanPcEpLicState                                     CucsLicenseState,
    cucsFabricEthLanPcEpLocale                                       CucsFabricExternalEpLocale,
    cucsFabricEthLanPcEpMembership                                   CucsFabricMembershipStatus,
    cucsFabricEthLanPcEpName                                         SnmpAdminString,
    cucsFabricEthLanPcEpPeerDn                                       SnmpAdminString,
    cucsFabricEthLanPcEpPeerPortId                                   Gauge32,
    cucsFabricEthLanPcEpPeerSlotId                                   Gauge32,
    cucsFabricEthLanPcEpPortId                                       Gauge32,
    cucsFabricEthLanPcEpSlotId                                       Gauge32,
    cucsFabricEthLanPcEpSwitchId                                     CucsNetworkSwitchId,
    cucsFabricEthLanPcEpTransport                                    CucsFabricAEthLanEpTransport,
    cucsFabricEthLanPcEpType                                         CucsFabricLanEpType,
    cucsFabricEthLanPcEpPeerChassisId                                Gauge32,
    cucsFabricEthLanPcEpFltAggr                                      Unsigned64
}

cucsFabricEthLanPcEpInstanceId OBJECT-TYPE
    SYNTAX       CucsManagedObjectId
    MAX-ACCESS   not-accessible
    STATUS       current
    DESCRIPTION
        "Instance identifier of the managed object."
    ::= { cucsFabricEthLanPcEpEntry 1 }

cucsFabricEthLanPcEpDn OBJECT-TYPE
    SYNTAX       CucsManagedObjectDn
    MAX-ACCESS   read-only
    STATUS       current
    DESCRIPTION
        "Cisco UCS fabric:EthLanPcEp:dn managed object property"
    ::= { cucsFabricEthLanPcEpEntry 2 }

cucsFabricEthLanPcEpRn OBJECT-TYPE
    SYNTAX       SnmpAdminString
    MAX-ACCESS   read-only
    STATUS       current
    DESCRIPTION
        "Cisco UCS fabric:EthLanPcEp:rn managed object property"
    ::= { cucsFabricEthLanPcEpEntry 3 }

cucsFabricEthLanPcEpAdminState OBJECT-TYPE
    SYNTAX       CucsFabricExternalEpAdminState
    MAX-ACCESS   read-only
    STATUS       current
    DESCRIPTION
        "Cisco UCS fabric:EthLanPcEp:adminState managed object property"
    ::= { cucsFabricEthLanPcEpEntry 4 }

cucsFabricEthLanPcEpChassisId OBJECT-TYPE
    SYNTAX       Gauge32
    MAX-ACCESS   read-only
    STATUS       current
    DESCRIPTION
        "Cisco UCS fabric:EthLanPcEp:chassisId managed object property"
    ::= { cucsFabricEthLanPcEpEntry 5 }

cucsFabricEthLanPcEpEpDn OBJECT-TYPE
    SYNTAX       SnmpAdminString
    MAX-ACCESS   read-only
    STATUS       current
    DESCRIPTION
        "Cisco UCS fabric:EthLanPcEp:epDn managed object property"
    ::= { cucsFabricEthLanPcEpEntry 6 }

cucsFabricEthLanPcEpIfRole OBJECT-TYPE
    SYNTAX       CucsFabricLanEpIfRole
    MAX-ACCESS   read-only
    STATUS       current
    DESCRIPTION
        "Cisco UCS fabric:EthLanPcEp:ifRole managed object property"
    ::= { cucsFabricEthLanPcEpEntry 7 }

cucsFabricEthLanPcEpIfType OBJECT-TYPE
    SYNTAX       CucsFabricPIoEpIfType
    MAX-ACCESS   read-only
    STATUS       current
    DESCRIPTION
        "Cisco UCS fabric:EthLanPcEp:ifType managed object property"
    ::= { cucsFabricEthLanPcEpEntry 8 }

cucsFabricEthLanPcEpLicGP OBJECT-TYPE
    SYNTAX       Unsigned64
    MAX-ACCESS   read-only
    STATUS       current
    DESCRIPTION
        "Cisco UCS fabric:EthLanPcEp:licGP managed object property"
    ::= { cucsFabricEthLanPcEpEntry 9 }

cucsFabricEthLanPcEpLicState OBJECT-TYPE
    SYNTAX       CucsLicenseState
    MAX-ACCESS   read-only
    STATUS       current
    DESCRIPTION
        "Cisco UCS fabric:EthLanPcEp:licState managed object property"
    ::= { cucsFabricEthLanPcEpEntry 10 }

cucsFabricEthLanPcEpLocale OBJECT-TYPE
    SYNTAX       CucsFabricExternalEpLocale
    MAX-ACCESS   read-only
    STATUS       current
    DESCRIPTION
        "Cisco UCS fabric:EthLanPcEp:locale managed object property"
    ::= { cucsFabricEthLanPcEpEntry 11 }

cucsFabricEthLanPcEpMembership OBJECT-TYPE
    SYNTAX       CucsFabricMembershipStatus
    MAX-ACCESS   read-only
    STATUS       current
    DESCRIPTION
        "Cisco UCS fabric:EthLanPcEp:membership managed object property"
    ::= { cucsFabricEthLanPcEpEntry 12 }

cucsFabricEthLanPcEpName OBJECT-TYPE
    SYNTAX       SnmpAdminString
    MAX-ACCESS   read-only
    STATUS       current
    DESCRIPTION
        "Cisco UCS fabric:EthLanPcEp:name managed object property"
    ::= { cucsFabricEthLanPcEpEntry 13 }

cucsFabricEthLanPcEpPeerDn OBJECT-TYPE
    SYNTAX       SnmpAdminString
    MAX-ACCESS   read-only
    STATUS       current
    DESCRIPTION
        "Cisco UCS fabric:EthLanPcEp:peerDn managed object property"
    ::= { cucsFabricEthLanPcEpEntry 14 }

cucsFabricEthLanPcEpPeerPortId OBJECT-TYPE
    SYNTAX       Gauge32
    MAX-ACCESS   read-only
    STATUS       current
    DESCRIPTION
        "Cisco UCS fabric:EthLanPcEp:peerPortId managed object property"
    ::= { cucsFabricEthLanPcEpEntry 15 }

cucsFabricEthLanPcEpPeerSlotId OBJECT-TYPE
    SYNTAX       Gauge32
    MAX-ACCESS   read-only
    STATUS       current
    DESCRIPTION
        "Cisco UCS fabric:EthLanPcEp:peerSlotId managed object property"
    ::= { cucsFabricEthLanPcEpEntry 16 }

cucsFabricEthLanPcEpPortId OBJECT-TYPE
    SYNTAX       Gauge32
    MAX-ACCESS   read-only
    STATUS       current
    DESCRIPTION
        "Cisco UCS fabric:EthLanPcEp:portId managed object property"
    ::= { cucsFabricEthLanPcEpEntry 17 }

cucsFabricEthLanPcEpSlotId OBJECT-TYPE
    SYNTAX       Gauge32
    MAX-ACCESS   read-only
    STATUS       current
    DESCRIPTION
        "Cisco UCS fabric:EthLanPcEp:slotId managed object property"
    ::= { cucsFabricEthLanPcEpEntry 18 }

cucsFabricEthLanPcEpSwitchId OBJECT-TYPE
    SYNTAX       CucsNetworkSwitchId
    MAX-ACCESS   read-only
    STATUS       current
    DESCRIPTION
        "Cisco UCS fabric:EthLanPcEp:switchId managed object property"
    ::= { cucsFabricEthLanPcEpEntry 19 }

cucsFabricEthLanPcEpTransport OBJECT-TYPE
    SYNTAX       CucsFabricAEthLanEpTransport
    MAX-ACCESS   read-only
    STATUS       current
    DESCRIPTION
        "Cisco UCS fabric:EthLanPcEp:transport managed object property"
    ::= { cucsFabricEthLanPcEpEntry 20 }

cucsFabricEthLanPcEpType OBJECT-TYPE
    SYNTAX       CucsFabricLanEpType
    MAX-ACCESS   read-only
    STATUS       current
    DESCRIPTION
        "Cisco UCS fabric:EthLanPcEp:type managed object property"
    ::= { cucsFabricEthLanPcEpEntry 21 }

cucsFabricEthLanPcEpPeerChassisId OBJECT-TYPE
    SYNTAX       Gauge32
    MAX-ACCESS   read-only
    STATUS       current
    DESCRIPTION
        "Cisco UCS fabric:EthLanPcEp:peerChassisId managed
        object property"
    ::= { cucsFabricEthLanPcEpEntry 22 }

cucsFabricEthLanPcEpFltAggr OBJECT-TYPE
    SYNTAX       Unsigned64
    MAX-ACCESS   read-only
    STATUS       current
    DESCRIPTION
        "Cisco UCS fabric:EthLanPcEp:fltAggr managed object property"
    ::= { cucsFabricEthLanPcEpEntry 23 }

cucsFabricEthMonTable OBJECT-TYPE
    SYNTAX           SEQUENCE OF CucsFabricEthMonEntry
    MAX-ACCESS       not-accessible
    STATUS           current
    DESCRIPTION
        "Cisco UCS fabric:EthMon managed object table"
    ::= { cucsFabricObjects 16 }

cucsFabricEthMonEntry OBJECT-TYPE
    SYNTAX           CucsFabricEthMonEntry
    MAX-ACCESS       not-accessible
    STATUS           current
    DESCRIPTION
        "Entry for the cucsFabricEthMonTable table."
    INDEX { cucsFabricEthMonInstanceId }
    ::= { cucsFabricEthMonTable 1 }

CucsFabricEthMonEntry ::= SEQUENCE {
    cucsFabricEthMonInstanceId                                       CucsManagedObjectId,
    cucsFabricEthMonDn                                               CucsManagedObjectDn,
    cucsFabricEthMonRn                                               SnmpAdminString,
    cucsFabricEthMonAdminState                                       CucsFabricMonAdminState,
    cucsFabricEthMonId                                               CucsNetworkSwitchId,
    cucsFabricEthMonLocale                                           CucsFabricExternalLocale,
    cucsFabricEthMonName                                             SnmpAdminString,
    cucsFabricEthMonSession                                          Gauge32,
    cucsFabricEthMonTransport                                        CucsFabricEthMonTransport,
    cucsFabricEthMonType                                             CucsFabricEthMonType,
    cucsFabricEthMonConfigFailReason                                 SnmpAdminString,
    cucsFabricEthMonIsConfigSuccess                                  TruthValue,
    cucsFabricEthMonOperState                                        CucsFabricMonOperState,
    cucsFabricEthMonOperStateReason                                  CucsFabricMonOperStateReason,
    cucsFabricEthMonPeerDn                                           SnmpAdminString
}

cucsFabricEthMonInstanceId OBJECT-TYPE
    SYNTAX       CucsManagedObjectId
    MAX-ACCESS   not-accessible
    STATUS       current
    DESCRIPTION
        "Instance identifier of the managed object."
    ::= { cucsFabricEthMonEntry 1 }

cucsFabricEthMonDn OBJECT-TYPE
    SYNTAX       CucsManagedObjectDn
    MAX-ACCESS   read-only
    STATUS       current
    DESCRIPTION
        "Cisco UCS fabric:EthMon:dn managed object property"
    ::= { cucsFabricEthMonEntry 2 }

cucsFabricEthMonRn OBJECT-TYPE
    SYNTAX       SnmpAdminString
    MAX-ACCESS   read-only
    STATUS       current
    DESCRIPTION
        "Cisco UCS fabric:EthMon:rn managed object property"
    ::= { cucsFabricEthMonEntry 3 }

cucsFabricEthMonAdminState OBJECT-TYPE
    SYNTAX       CucsFabricMonAdminState
    MAX-ACCESS   read-only
    STATUS       current
    DESCRIPTION
        "Cisco UCS fabric:EthMon:adminState managed object property"
    ::= { cucsFabricEthMonEntry 4 }

cucsFabricEthMonId OBJECT-TYPE
    SYNTAX       CucsNetworkSwitchId
    MAX-ACCESS   read-only
    STATUS       current
    DESCRIPTION
        "Cisco UCS fabric:EthMon:id managed object property"
    ::= { cucsFabricEthMonEntry 5 }

cucsFabricEthMonLocale OBJECT-TYPE
    SYNTAX       CucsFabricExternalLocale
    MAX-ACCESS   read-only
    STATUS       current
    DESCRIPTION
        "Cisco UCS fabric:EthMon:locale managed object property"
    ::= { cucsFabricEthMonEntry 6 }

cucsFabricEthMonName OBJECT-TYPE
    SYNTAX       SnmpAdminString
    MAX-ACCESS   read-only
    STATUS       current
    DESCRIPTION
        "Cisco UCS fabric:EthMon:name managed object property"
    ::= { cucsFabricEthMonEntry 7 }

cucsFabricEthMonSession OBJECT-TYPE
    SYNTAX       Gauge32
    MAX-ACCESS   read-only
    STATUS       current
    DESCRIPTION
        "Cisco UCS fabric:EthMon:session managed object property"
    ::= { cucsFabricEthMonEntry 8 }

cucsFabricEthMonTransport OBJECT-TYPE
    SYNTAX       CucsFabricEthMonTransport
    MAX-ACCESS   read-only
    STATUS       current
    DESCRIPTION
        "Cisco UCS fabric:EthMon:transport managed object property"
    ::= { cucsFabricEthMonEntry 9 }

cucsFabricEthMonType OBJECT-TYPE
    SYNTAX       CucsFabricEthMonType
    MAX-ACCESS   read-only
    STATUS       current
    DESCRIPTION
        "Cisco UCS fabric:EthMon:type managed object property"
    ::= { cucsFabricEthMonEntry 10 }

cucsFabricEthMonConfigFailReason OBJECT-TYPE
    SYNTAX       SnmpAdminString
    MAX-ACCESS   read-only
    STATUS       current
    DESCRIPTION
        "Cisco UCS fabric:EthMon:configFailReason managed object property"
    ::= { cucsFabricEthMonEntry 11 }

cucsFabricEthMonIsConfigSuccess OBJECT-TYPE
    SYNTAX       TruthValue
    MAX-ACCESS   read-only
    STATUS       current
    DESCRIPTION
        "Cisco UCS fabric:EthMon:isConfigSuccess managed object property"
    ::= { cucsFabricEthMonEntry 12 }

cucsFabricEthMonOperState OBJECT-TYPE
    SYNTAX       CucsFabricMonOperState
    MAX-ACCESS   read-only
    STATUS       current
    DESCRIPTION
        "Cisco UCS fabric:EthMon:operState managed object property"
    ::= { cucsFabricEthMonEntry 13 }

cucsFabricEthMonOperStateReason OBJECT-TYPE
    SYNTAX       CucsFabricMonOperStateReason
    MAX-ACCESS   read-only
    STATUS       current
    DESCRIPTION
        "Cisco UCS fabric:EthMon:operStateReason managed object property"
    ::= { cucsFabricEthMonEntry 14 }

cucsFabricEthMonPeerDn OBJECT-TYPE
    SYNTAX       SnmpAdminString
    MAX-ACCESS   read-only
    STATUS       current
    DESCRIPTION
        "Cisco UCS fabric:EthMon:peerDn managed object property"
    ::= { cucsFabricEthMonEntry 15 }

cucsFabricEthMonDestEpTable OBJECT-TYPE
    SYNTAX           SEQUENCE OF CucsFabricEthMonDestEpEntry
    MAX-ACCESS       not-accessible
    STATUS           current
    DESCRIPTION
        "Cisco UCS fabric:EthMonDestEp managed object table"
    ::= { cucsFabricObjects 17 }

cucsFabricEthMonDestEpEntry OBJECT-TYPE
    SYNTAX           CucsFabricEthMonDestEpEntry
    MAX-ACCESS       not-accessible
    STATUS           current
    DESCRIPTION
        "Entry for the cucsFabricEthMonDestEpTable table."
    INDEX { cucsFabricEthMonDestEpInstanceId }
    ::= { cucsFabricEthMonDestEpTable 1 }

CucsFabricEthMonDestEpEntry ::= SEQUENCE {
    cucsFabricEthMonDestEpInstanceId                                 CucsManagedObjectId,
    cucsFabricEthMonDestEpDn                                         CucsManagedObjectDn,
    cucsFabricEthMonDestEpRn                                         SnmpAdminString,
    cucsFabricEthMonDestEpAdminState                                 CucsFabricExternalEpAdminState,
    cucsFabricEthMonDestEpChassisId                                  Gauge32,
    cucsFabricEthMonDestEpEpDn                                       SnmpAdminString,
    cucsFabricEthMonDestEpIfRole                                     CucsFabricEthMonDestEpIfRole,
    cucsFabricEthMonDestEpIfType                                     CucsFabricPIoEpIfType,
    cucsFabricEthMonDestEpLicGP                                      Unsigned64,
    cucsFabricEthMonDestEpLicState                                   CucsLicenseState,
    cucsFabricEthMonDestEpLocale                                     CucsFabricExternalEpLocale,
    cucsFabricEthMonDestEpName                                       SnmpAdminString,
    cucsFabricEthMonDestEpPeerDn                                     SnmpAdminString,
    cucsFabricEthMonDestEpPeerPortId                                 Gauge32,
    cucsFabricEthMonDestEpPeerSlotId                                 Gauge32,
    cucsFabricEthMonDestEpPortId                                     CucsFabricEthMonDestEpPortId,
    cucsFabricEthMonDestEpSlotId                                     CucsFabricEthMonDestEpSlotId,
    cucsFabricEthMonDestEpSwitchId                                   CucsNetworkSwitchId,
    cucsFabricEthMonDestEpTransport                                  CucsNetworkTransport,
    cucsFabricEthMonDestEpType                                       CucsFabricEthMonDestEpType,
    cucsFabricEthMonDestEpPeerChassisId                              Gauge32,
    cucsFabricEthMonDestEpFltAggr                                    Unsigned64
}

cucsFabricEthMonDestEpInstanceId OBJECT-TYPE
    SYNTAX       CucsManagedObjectId
    MAX-ACCESS   not-accessible
    STATUS       current
    DESCRIPTION
        "Instance identifier of the managed object."
    ::= { cucsFabricEthMonDestEpEntry 1 }

cucsFabricEthMonDestEpDn OBJECT-TYPE
    SYNTAX       CucsManagedObjectDn
    MAX-ACCESS   read-only
    STATUS       current
    DESCRIPTION
        "Cisco UCS fabric:EthMonDestEp:dn managed object property"
    ::= { cucsFabricEthMonDestEpEntry 2 }

cucsFabricEthMonDestEpRn OBJECT-TYPE
    SYNTAX       SnmpAdminString
    MAX-ACCESS   read-only
    STATUS       current
    DESCRIPTION
        "Cisco UCS fabric:EthMonDestEp:rn managed object property"
    ::= { cucsFabricEthMonDestEpEntry 3 }

cucsFabricEthMonDestEpAdminState OBJECT-TYPE
    SYNTAX       CucsFabricExternalEpAdminState
    MAX-ACCESS   read-only
    STATUS       current
    DESCRIPTION
        "Cisco UCS fabric:EthMonDestEp:adminState managed object property"
    ::= { cucsFabricEthMonDestEpEntry 4 }

cucsFabricEthMonDestEpChassisId OBJECT-TYPE
    SYNTAX       Gauge32
    MAX-ACCESS   read-only
    STATUS       current
    DESCRIPTION
        "Cisco UCS fabric:EthMonDestEp:chassisId managed object property"
    ::= { cucsFabricEthMonDestEpEntry 5 }

cucsFabricEthMonDestEpEpDn OBJECT-TYPE
    SYNTAX       SnmpAdminString
    MAX-ACCESS   read-only
    STATUS       current
    DESCRIPTION
        "Cisco UCS fabric:EthMonDestEp:epDn managed object property"
    ::= { cucsFabricEthMonDestEpEntry 6 }

cucsFabricEthMonDestEpIfRole OBJECT-TYPE
    SYNTAX       CucsFabricEthMonDestEpIfRole
    MAX-ACCESS   read-only
    STATUS       current
    DESCRIPTION
        "Cisco UCS fabric:EthMonDestEp:ifRole managed object property"
    ::= { cucsFabricEthMonDestEpEntry 7 }

cucsFabricEthMonDestEpIfType OBJECT-TYPE
    SYNTAX       CucsFabricPIoEpIfType
    MAX-ACCESS   read-only
    STATUS       current
    DESCRIPTION
        "Cisco UCS fabric:EthMonDestEp:ifType managed object property"
    ::= { cucsFabricEthMonDestEpEntry 8 }

cucsFabricEthMonDestEpLicGP OBJECT-TYPE
    SYNTAX       Unsigned64
    MAX-ACCESS   read-only
    STATUS       current
    DESCRIPTION
        "Cisco UCS fabric:EthMonDestEp:licGP managed object property"
    ::= { cucsFabricEthMonDestEpEntry 9 }

cucsFabricEthMonDestEpLicState OBJECT-TYPE
    SYNTAX       CucsLicenseState
    MAX-ACCESS   read-only
    STATUS       current
    DESCRIPTION
        "Cisco UCS fabric:EthMonDestEp:licState managed object property"
    ::= { cucsFabricEthMonDestEpEntry 10 }

cucsFabricEthMonDestEpLocale OBJECT-TYPE
    SYNTAX       CucsFabricExternalEpLocale
    MAX-ACCESS   read-only
    STATUS       current
    DESCRIPTION
        "Cisco UCS fabric:EthMonDestEp:locale managed object property"
    ::= { cucsFabricEthMonDestEpEntry 11 }

cucsFabricEthMonDestEpName OBJECT-TYPE
    SYNTAX       SnmpAdminString
    MAX-ACCESS   read-only
    STATUS       current
    DESCRIPTION
        "Cisco UCS fabric:EthMonDestEp:name managed object property"
    ::= { cucsFabricEthMonDestEpEntry 12 }

cucsFabricEthMonDestEpPeerDn OBJECT-TYPE
    SYNTAX       SnmpAdminString
    MAX-ACCESS   read-only
    STATUS       current
    DESCRIPTION
        "Cisco UCS fabric:EthMonDestEp:peerDn managed object property"
    ::= { cucsFabricEthMonDestEpEntry 13 }

cucsFabricEthMonDestEpPeerPortId OBJECT-TYPE
    SYNTAX       Gauge32
    MAX-ACCESS   read-only
    STATUS       current
    DESCRIPTION
        "Cisco UCS fabric:EthMonDestEp:peerPortId managed object property"
    ::= { cucsFabricEthMonDestEpEntry 14 }

cucsFabricEthMonDestEpPeerSlotId OBJECT-TYPE
    SYNTAX       Gauge32
    MAX-ACCESS   read-only
    STATUS       current
    DESCRIPTION
        "Cisco UCS fabric:EthMonDestEp:peerSlotId managed object property"
    ::= { cucsFabricEthMonDestEpEntry 15 }

cucsFabricEthMonDestEpPortId OBJECT-TYPE
    SYNTAX       CucsFabricEthMonDestEpPortId
    MAX-ACCESS   read-only
    STATUS       current
    DESCRIPTION
        "Cisco UCS fabric:EthMonDestEp:portId managed object property"
    ::= { cucsFabricEthMonDestEpEntry 16 }

cucsFabricEthMonDestEpSlotId OBJECT-TYPE
    SYNTAX       CucsFabricEthMonDestEpSlotId
    MAX-ACCESS   read-only
    STATUS       current
    DESCRIPTION
        "Cisco UCS fabric:EthMonDestEp:slotId managed object property"
    ::= { cucsFabricEthMonDestEpEntry 17 }

cucsFabricEthMonDestEpSwitchId OBJECT-TYPE
    SYNTAX       CucsNetworkSwitchId
    MAX-ACCESS   read-only
    STATUS       current
    DESCRIPTION
        "Cisco UCS fabric:EthMonDestEp:switchId managed object property"
    ::= { cucsFabricEthMonDestEpEntry 18 }

cucsFabricEthMonDestEpTransport OBJECT-TYPE
    SYNTAX       CucsNetworkTransport
    MAX-ACCESS   read-only
    STATUS       current
    DESCRIPTION
        "Cisco UCS fabric:EthMonDestEp:transport managed object property"
    ::= { cucsFabricEthMonDestEpEntry 19 }

cucsFabricEthMonDestEpType OBJECT-TYPE
    SYNTAX       CucsFabricEthMonDestEpType
    MAX-ACCESS   read-only
    STATUS       current
    DESCRIPTION
        "Cisco UCS fabric:EthMonDestEp:type managed object property"
    ::= { cucsFabricEthMonDestEpEntry 20 }

cucsFabricEthMonDestEpPeerChassisId OBJECT-TYPE
    SYNTAX       Gauge32
    MAX-ACCESS   read-only
    STATUS       current
    DESCRIPTION
        "Cisco UCS fabric:EthMonDestEp:peerChassisId managed
        object property"
    ::= { cucsFabricEthMonDestEpEntry 21 }

cucsFabricEthMonDestEpFltAggr OBJECT-TYPE
    SYNTAX       Unsigned64
    MAX-ACCESS   read-only
    STATUS       current
    DESCRIPTION
        "Cisco UCS fabric:EthMonDestEp:fltAggr managed object property"
    ::= { cucsFabricEthMonDestEpEntry 22 }

cucsFabricEthMonFiltEpTable OBJECT-TYPE
    SYNTAX           SEQUENCE OF CucsFabricEthMonFiltEpEntry
    MAX-ACCESS       not-accessible
    STATUS           current
    DESCRIPTION
        "Cisco UCS fabric:EthMonFiltEp managed object table"
    ::= { cucsFabricObjects 18 }

cucsFabricEthMonFiltEpEntry OBJECT-TYPE
    SYNTAX           CucsFabricEthMonFiltEpEntry
    MAX-ACCESS       not-accessible
    STATUS           current
    DESCRIPTION
        "Entry for the cucsFabricEthMonFiltEpTable table."
    INDEX { cucsFabricEthMonFiltEpInstanceId }
    ::= { cucsFabricEthMonFiltEpTable 1 }

CucsFabricEthMonFiltEpEntry ::= SEQUENCE {
    cucsFabricEthMonFiltEpInstanceId                                 CucsManagedObjectId,
    cucsFabricEthMonFiltEpDn                                         CucsManagedObjectDn,
    cucsFabricEthMonFiltEpRn                                         SnmpAdminString,
    cucsFabricEthMonFiltEpName                                       SnmpAdminString,
    cucsFabricEthMonFiltEpSession                                    Gauge32,
    cucsFabricEthMonFiltEpType                                       CucsFabricEthMonFiltEpType
}

cucsFabricEthMonFiltEpInstanceId OBJECT-TYPE
    SYNTAX       CucsManagedObjectId
    MAX-ACCESS   not-accessible
    STATUS       current
    DESCRIPTION
        "Instance identifier of the managed object."
    ::= { cucsFabricEthMonFiltEpEntry 1 }

cucsFabricEthMonFiltEpDn OBJECT-TYPE
    SYNTAX       CucsManagedObjectDn
    MAX-ACCESS   read-only
    STATUS       current
    DESCRIPTION
        "Cisco UCS fabric:EthMonFiltEp:dn managed object property"
    ::= { cucsFabricEthMonFiltEpEntry 2 }

cucsFabricEthMonFiltEpRn OBJECT-TYPE
    SYNTAX       SnmpAdminString
    MAX-ACCESS   read-only
    STATUS       current
    DESCRIPTION
        "Cisco UCS fabric:EthMonFiltEp:rn managed object property"
    ::= { cucsFabricEthMonFiltEpEntry 3 }

cucsFabricEthMonFiltEpName OBJECT-TYPE
    SYNTAX       SnmpAdminString
    MAX-ACCESS   read-only
    STATUS       current
    DESCRIPTION
        "Cisco UCS fabric:EthMonFiltEp:name managed object property"
    ::= { cucsFabricEthMonFiltEpEntry 4 }

cucsFabricEthMonFiltEpSession OBJECT-TYPE
    SYNTAX       Gauge32
    MAX-ACCESS   read-only
    STATUS       current
    DESCRIPTION
        "Cisco UCS fabric:EthMonFiltEp:session managed object property"
    ::= { cucsFabricEthMonFiltEpEntry 5 }

cucsFabricEthMonFiltEpType OBJECT-TYPE
    SYNTAX       CucsFabricEthMonFiltEpType
    MAX-ACCESS   read-only
    STATUS       current
    DESCRIPTION
        "Cisco UCS fabric:EthMonFiltEp:type managed object property"
    ::= { cucsFabricEthMonFiltEpEntry 6 }

cucsFabricEthMonFiltRefTable OBJECT-TYPE
    SYNTAX           SEQUENCE OF CucsFabricEthMonFiltRefEntry
    MAX-ACCESS       not-accessible
    STATUS           current
    DESCRIPTION
        "Cisco UCS fabric:EthMonFiltRef managed object table"
    ::= { cucsFabricObjects 19 }

cucsFabricEthMonFiltRefEntry OBJECT-TYPE
    SYNTAX           CucsFabricEthMonFiltRefEntry
    MAX-ACCESS       not-accessible
    STATUS           current
    DESCRIPTION
        "Entry for the cucsFabricEthMonFiltRefTable table."
    INDEX { cucsFabricEthMonFiltRefInstanceId }
    ::= { cucsFabricEthMonFiltRefTable 1 }

CucsFabricEthMonFiltRefEntry ::= SEQUENCE {
    cucsFabricEthMonFiltRefInstanceId                                CucsManagedObjectId,
    cucsFabricEthMonFiltRefDn                                        CucsManagedObjectDn,
    cucsFabricEthMonFiltRefRn                                        SnmpAdminString,
    cucsFabricEthMonFiltRefSrcFiltDn                                 SnmpAdminString,
    cucsFabricEthMonFiltRefType                                      CucsFabricEthMonFiltRefType
}

cucsFabricEthMonFiltRefInstanceId OBJECT-TYPE
    SYNTAX       CucsManagedObjectId
    MAX-ACCESS   not-accessible
    STATUS       current
    DESCRIPTION
        "Instance identifier of the managed object."
    ::= { cucsFabricEthMonFiltRefEntry 1 }

cucsFabricEthMonFiltRefDn OBJECT-TYPE
    SYNTAX       CucsManagedObjectDn
    MAX-ACCESS   read-only
    STATUS       current
    DESCRIPTION
        "Cisco UCS fabric:EthMonFiltRef:dn managed object property"
    ::= { cucsFabricEthMonFiltRefEntry 2 }

cucsFabricEthMonFiltRefRn OBJECT-TYPE
    SYNTAX       SnmpAdminString
    MAX-ACCESS   read-only
    STATUS       current
    DESCRIPTION
        "Cisco UCS fabric:EthMonFiltRef:rn managed object property"
    ::= { cucsFabricEthMonFiltRefEntry 3 }

cucsFabricEthMonFiltRefSrcFiltDn OBJECT-TYPE
    SYNTAX       SnmpAdminString
    MAX-ACCESS   read-only
    STATUS       current
    DESCRIPTION
        "Cisco UCS fabric:EthMonFiltRef:srcFiltDn managed object property"
    ::= { cucsFabricEthMonFiltRefEntry 4 }

cucsFabricEthMonFiltRefType OBJECT-TYPE
    SYNTAX       CucsFabricEthMonFiltRefType
    MAX-ACCESS   read-only
    STATUS       current
    DESCRIPTION
        "Cisco UCS fabric:EthMonFiltRef:type managed object property"
    ::= { cucsFabricEthMonFiltRefEntry 5 }

cucsFabricEthMonLanTable OBJECT-TYPE
    SYNTAX           SEQUENCE OF CucsFabricEthMonLanEntry
    MAX-ACCESS       not-accessible
    STATUS           current
    DESCRIPTION
        "Cisco UCS fabric:EthMonLan managed object table"
    ::= { cucsFabricObjects 20 }

cucsFabricEthMonLanEntry OBJECT-TYPE
    SYNTAX           CucsFabricEthMonLanEntry
    MAX-ACCESS       not-accessible
    STATUS           current
    DESCRIPTION
        "Entry for the cucsFabricEthMonLanTable table."
    INDEX { cucsFabricEthMonLanInstanceId }
    ::= { cucsFabricEthMonLanTable 1 }

CucsFabricEthMonLanEntry ::= SEQUENCE {
    cucsFabricEthMonLanInstanceId                                    CucsManagedObjectId,
    cucsFabricEthMonLanDn                                            CucsManagedObjectDn,
    cucsFabricEthMonLanRn                                            SnmpAdminString,
    cucsFabricEthMonLanId                                            CucsNetworkSwitchId,
    cucsFabricEthMonLanLocale                                        CucsFabricExternalLocale,
    cucsFabricEthMonLanName                                          SnmpAdminString,
    cucsFabricEthMonLanTransport                                     CucsFabricEthMonLanTransport,
    cucsFabricEthMonLanType                                          CucsFabricEthMonLanType
}

cucsFabricEthMonLanInstanceId OBJECT-TYPE
    SYNTAX       CucsManagedObjectId
    MAX-ACCESS   not-accessible
    STATUS       current
    DESCRIPTION
        "Instance identifier of the managed object."
    ::= { cucsFabricEthMonLanEntry 1 }

cucsFabricEthMonLanDn OBJECT-TYPE
    SYNTAX       CucsManagedObjectDn
    MAX-ACCESS   read-only
    STATUS       current
    DESCRIPTION
        "Cisco UCS fabric:EthMonLan:dn managed object property"
    ::= { cucsFabricEthMonLanEntry 2 }

cucsFabricEthMonLanRn OBJECT-TYPE
    SYNTAX       SnmpAdminString
    MAX-ACCESS   read-only
    STATUS       current
    DESCRIPTION
        "Cisco UCS fabric:EthMonLan:rn managed object property"
    ::= { cucsFabricEthMonLanEntry 3 }

cucsFabricEthMonLanId OBJECT-TYPE
    SYNTAX       CucsNetworkSwitchId
    MAX-ACCESS   read-only
    STATUS       current
    DESCRIPTION
        "Cisco UCS fabric:EthMonLan:id managed object property"
    ::= { cucsFabricEthMonLanEntry 4 }

cucsFabricEthMonLanLocale OBJECT-TYPE
    SYNTAX       CucsFabricExternalLocale
    MAX-ACCESS   read-only
    STATUS       current
    DESCRIPTION
        "Cisco UCS fabric:EthMonLan:locale managed object property"
    ::= { cucsFabricEthMonLanEntry 5 }

cucsFabricEthMonLanName OBJECT-TYPE
    SYNTAX       SnmpAdminString
    MAX-ACCESS   read-only
    STATUS       current
    DESCRIPTION
        "Cisco UCS fabric:EthMonLan:name managed object property"
    ::= { cucsFabricEthMonLanEntry 6 }

cucsFabricEthMonLanTransport OBJECT-TYPE
    SYNTAX       CucsFabricEthMonLanTransport
    MAX-ACCESS   read-only
    STATUS       current
    DESCRIPTION
        "Cisco UCS fabric:EthMonLan:transport managed object property"
    ::= { cucsFabricEthMonLanEntry 7 }

cucsFabricEthMonLanType OBJECT-TYPE
    SYNTAX       CucsFabricEthMonLanType
    MAX-ACCESS   read-only
    STATUS       current
    DESCRIPTION
        "Cisco UCS fabric:EthMonLan:type managed object property"
    ::= { cucsFabricEthMonLanEntry 8 }

cucsFabricEthMonSrcEpTable OBJECT-TYPE
    SYNTAX           SEQUENCE OF CucsFabricEthMonSrcEpEntry
    MAX-ACCESS       not-accessible
    STATUS           current
    DESCRIPTION
        "Cisco UCS fabric:EthMonSrcEp managed object table"
    ::= { cucsFabricObjects 21 }

cucsFabricEthMonSrcEpEntry OBJECT-TYPE
    SYNTAX           CucsFabricEthMonSrcEpEntry
    MAX-ACCESS       not-accessible
    STATUS           current
    DESCRIPTION
        "Entry for the cucsFabricEthMonSrcEpTable table."
    INDEX { cucsFabricEthMonSrcEpInstanceId }
    ::= { cucsFabricEthMonSrcEpTable 1 }

CucsFabricEthMonSrcEpEntry ::= SEQUENCE {
    cucsFabricEthMonSrcEpInstanceId                                  CucsManagedObjectId,
    cucsFabricEthMonSrcEpDn                                          CucsManagedObjectDn,
    cucsFabricEthMonSrcEpRn                                          SnmpAdminString,
    cucsFabricEthMonSrcEpDirection                                   CucsFabricTrafficDirection,
    cucsFabricEthMonSrcEpName                                        SnmpAdminString,
    cucsFabricEthMonSrcEpSession                                     Gauge32,
    cucsFabricEthMonSrcEpTransport                                   CucsNetworkTransport,
    cucsFabricEthMonSrcEpType                                        CucsFabricEthMonSrcEpType
}

cucsFabricEthMonSrcEpInstanceId OBJECT-TYPE
    SYNTAX       CucsManagedObjectId
    MAX-ACCESS   not-accessible
    STATUS       current
    DESCRIPTION
        "Instance identifier of the managed object."
    ::= { cucsFabricEthMonSrcEpEntry 1 }

cucsFabricEthMonSrcEpDn OBJECT-TYPE
    SYNTAX       CucsManagedObjectDn
    MAX-ACCESS   read-only
    STATUS       current
    DESCRIPTION
        "Cisco UCS fabric:EthMonSrcEp:dn managed object property"
    ::= { cucsFabricEthMonSrcEpEntry 2 }

cucsFabricEthMonSrcEpRn OBJECT-TYPE
    SYNTAX       SnmpAdminString
    MAX-ACCESS   read-only
    STATUS       current
    DESCRIPTION
        "Cisco UCS fabric:EthMonSrcEp:rn managed object property"
    ::= { cucsFabricEthMonSrcEpEntry 3 }

cucsFabricEthMonSrcEpDirection OBJECT-TYPE
    SYNTAX       CucsFabricTrafficDirection
    MAX-ACCESS   read-only
    STATUS       current
    DESCRIPTION
        "Cisco UCS fabric:EthMonSrcEp:direction managed object property"
    ::= { cucsFabricEthMonSrcEpEntry 4 }

cucsFabricEthMonSrcEpName OBJECT-TYPE
    SYNTAX       SnmpAdminString
    MAX-ACCESS   read-only
    STATUS       current
    DESCRIPTION
        "Cisco UCS fabric:EthMonSrcEp:name managed object property"
    ::= { cucsFabricEthMonSrcEpEntry 5 }

cucsFabricEthMonSrcEpSession OBJECT-TYPE
    SYNTAX       Gauge32
    MAX-ACCESS   read-only
    STATUS       current
    DESCRIPTION
        "Cisco UCS fabric:EthMonSrcEp:session managed object property"
    ::= { cucsFabricEthMonSrcEpEntry 6 }

cucsFabricEthMonSrcEpTransport OBJECT-TYPE
    SYNTAX       CucsNetworkTransport
    MAX-ACCESS   read-only
    STATUS       current
    DESCRIPTION
        "Cisco UCS fabric:EthMonSrcEp:transport managed object property"
    ::= { cucsFabricEthMonSrcEpEntry 7 }

cucsFabricEthMonSrcEpType OBJECT-TYPE
    SYNTAX       CucsFabricEthMonSrcEpType
    MAX-ACCESS   read-only
    STATUS       current
    DESCRIPTION
        "Cisco UCS fabric:EthMonSrcEp:type managed object property"
    ::= { cucsFabricEthMonSrcEpEntry 8 }

cucsFabricEthMonSrcRefTable OBJECT-TYPE
    SYNTAX           SEQUENCE OF CucsFabricEthMonSrcRefEntry
    MAX-ACCESS       not-accessible
    STATUS           current
    DESCRIPTION
        "Cisco UCS fabric:EthMonSrcRef managed object table"
    ::= { cucsFabricObjects 22 }

cucsFabricEthMonSrcRefEntry OBJECT-TYPE
    SYNTAX           CucsFabricEthMonSrcRefEntry
    MAX-ACCESS       not-accessible
    STATUS           current
    DESCRIPTION
        "Entry for the cucsFabricEthMonSrcRefTable table."
    INDEX { cucsFabricEthMonSrcRefInstanceId }
    ::= { cucsFabricEthMonSrcRefTable 1 }

CucsFabricEthMonSrcRefEntry ::= SEQUENCE {
    cucsFabricEthMonSrcRefInstanceId                                 CucsManagedObjectId,
    cucsFabricEthMonSrcRefDn                                         CucsManagedObjectDn,
    cucsFabricEthMonSrcRefRn                                         SnmpAdminString,
    cucsFabricEthMonSrcRefId                                         Unsigned64,
    cucsFabricEthMonSrcRefSourceDn                                   SnmpAdminString,
    cucsFabricEthMonSrcRefSourceType                                 CucsFabricEthSourceType,
    cucsFabricEthMonSrcRefType                                       CucsFabricEthMonSrcRefType
}

cucsFabricEthMonSrcRefInstanceId OBJECT-TYPE
    SYNTAX       CucsManagedObjectId
    MAX-ACCESS   not-accessible
    STATUS       current
    DESCRIPTION
        "Instance identifier of the managed object."
    ::= { cucsFabricEthMonSrcRefEntry 1 }

cucsFabricEthMonSrcRefDn OBJECT-TYPE
    SYNTAX       CucsManagedObjectDn
    MAX-ACCESS   read-only
    STATUS       current
    DESCRIPTION
        "Cisco UCS fabric:EthMonSrcRef:dn managed object property"
    ::= { cucsFabricEthMonSrcRefEntry 2 }

cucsFabricEthMonSrcRefRn OBJECT-TYPE
    SYNTAX       SnmpAdminString
    MAX-ACCESS   read-only
    STATUS       current
    DESCRIPTION
        "Cisco UCS fabric:EthMonSrcRef:rn managed object property"
    ::= { cucsFabricEthMonSrcRefEntry 3 }

cucsFabricEthMonSrcRefId OBJECT-TYPE
    SYNTAX       Unsigned64
    MAX-ACCESS   read-only
    STATUS       current
    DESCRIPTION
        "Cisco UCS fabric:EthMonSrcRef:id managed object property"
    ::= { cucsFabricEthMonSrcRefEntry 4 }

cucsFabricEthMonSrcRefSourceDn OBJECT-TYPE
    SYNTAX       SnmpAdminString
    MAX-ACCESS   read-only
    STATUS       current
    DESCRIPTION
        "Cisco UCS fabric:EthMonSrcRef:sourceDn managed object property"
    ::= { cucsFabricEthMonSrcRefEntry 5 }

cucsFabricEthMonSrcRefSourceType OBJECT-TYPE
    SYNTAX       CucsFabricEthSourceType
    MAX-ACCESS   read-only
    STATUS       current
    DESCRIPTION
        "Cisco UCS fabric:EthMonSrcRef:sourceType managed object property"
    ::= { cucsFabricEthMonSrcRefEntry 6 }

cucsFabricEthMonSrcRefType OBJECT-TYPE
    SYNTAX       CucsFabricEthMonSrcRefType
    MAX-ACCESS   read-only
    STATUS       current
    DESCRIPTION
        "Cisco UCS fabric:EthMonSrcRef:type managed object property"
    ::= { cucsFabricEthMonSrcRefEntry 7 }

cucsFabricEthTargetEpTable OBJECT-TYPE
    SYNTAX           SEQUENCE OF CucsFabricEthTargetEpEntry
    MAX-ACCESS       not-accessible
    STATUS           current
    DESCRIPTION
        "Cisco UCS fabric:EthTargetEp managed object table"
    ::= { cucsFabricObjects 23 }

cucsFabricEthTargetEpEntry OBJECT-TYPE
    SYNTAX           CucsFabricEthTargetEpEntry
    MAX-ACCESS       not-accessible
    STATUS           current
    DESCRIPTION
        "Entry for the cucsFabricEthTargetEpTable table."
    INDEX { cucsFabricEthTargetEpInstanceId }
    ::= { cucsFabricEthTargetEpTable 1 }

CucsFabricEthTargetEpEntry ::= SEQUENCE {
    cucsFabricEthTargetEpInstanceId                                  CucsManagedObjectId,
    cucsFabricEthTargetEpDn                                          CucsManagedObjectDn,
    cucsFabricEthTargetEpRn                                          SnmpAdminString,
    cucsFabricEthTargetEpAdminState                                  CucsFabricExternalEpAdminState,
    cucsFabricEthTargetEpChassisId                                   Gauge32,
    cucsFabricEthTargetEpEpDn                                        SnmpAdminString,
    cucsFabricEthTargetEpIfRole                                      CucsNetworkPortRole,
    cucsFabricEthTargetEpIfType                                      CucsFabricPIoEpIfType,
    cucsFabricEthTargetEpLicGP                                       Unsigned64,
    cucsFabricEthTargetEpLicState                                    CucsLicenseState,
    cucsFabricEthTargetEpLocale                                      CucsFabricExternalEpLocale,
    cucsFabricEthTargetEpMacAddress                                  MacAddress,
    cucsFabricEthTargetEpName                                        SnmpAdminString,
    cucsFabricEthTargetEpPeerDn                                      SnmpAdminString,
    cucsFabricEthTargetEpPeerPortId                                  Gauge32,
    cucsFabricEthTargetEpPeerSlotId                                  Gauge32,
    cucsFabricEthTargetEpPortId                                      CucsFabricPIoEpPortId,
    cucsFabricEthTargetEpSlotId                                      CucsFabricPIoEpSlotId,
    cucsFabricEthTargetEpSwitchId                                    CucsNetworkSwitchId,
    cucsFabricEthTargetEpTransport                                   CucsFabricEthTargetEpTransport,
    cucsFabricEthTargetEpType                                        CucsFabricTargetEpType,
    cucsFabricEthTargetEpPeerChassisId                               Gauge32,
    cucsFabricEthTargetEpFltAggr                                     Unsigned64
}

cucsFabricEthTargetEpInstanceId OBJECT-TYPE
    SYNTAX       CucsManagedObjectId
    MAX-ACCESS   not-accessible
    STATUS       current
    DESCRIPTION
        "Instance identifier of the managed object."
    ::= { cucsFabricEthTargetEpEntry 1 }

cucsFabricEthTargetEpDn OBJECT-TYPE
    SYNTAX       CucsManagedObjectDn
    MAX-ACCESS   read-only
    STATUS       current
    DESCRIPTION
        "Cisco UCS fabric:EthTargetEp:dn managed object property"
    ::= { cucsFabricEthTargetEpEntry 2 }

cucsFabricEthTargetEpRn OBJECT-TYPE
    SYNTAX       SnmpAdminString
    MAX-ACCESS   read-only
    STATUS       current
    DESCRIPTION
        "Cisco UCS fabric:EthTargetEp:rn managed object property"
    ::= { cucsFabricEthTargetEpEntry 3 }

cucsFabricEthTargetEpAdminState OBJECT-TYPE
    SYNTAX       CucsFabricExternalEpAdminState
    MAX-ACCESS   read-only
    STATUS       current
    DESCRIPTION
        "Cisco UCS fabric:EthTargetEp:adminState managed object property"
    ::= { cucsFabricEthTargetEpEntry 4 }

cucsFabricEthTargetEpChassisId OBJECT-TYPE
    SYNTAX       Gauge32
    MAX-ACCESS   read-only
    STATUS       current
    DESCRIPTION
        "Cisco UCS fabric:EthTargetEp:chassisId managed object property"
    ::= { cucsFabricEthTargetEpEntry 5 }

cucsFabricEthTargetEpEpDn OBJECT-TYPE
    SYNTAX       SnmpAdminString
    MAX-ACCESS   read-only
    STATUS       current
    DESCRIPTION
        "Cisco UCS fabric:EthTargetEp:epDn managed object property"
    ::= { cucsFabricEthTargetEpEntry 6 }

cucsFabricEthTargetEpIfRole OBJECT-TYPE
    SYNTAX       CucsNetworkPortRole
    MAX-ACCESS   read-only
    STATUS       current
    DESCRIPTION
        "Cisco UCS fabric:EthTargetEp:ifRole managed object property"
    ::= { cucsFabricEthTargetEpEntry 7 }

cucsFabricEthTargetEpIfType OBJECT-TYPE
    SYNTAX       CucsFabricPIoEpIfType
    MAX-ACCESS   read-only
    STATUS       current
    DESCRIPTION
        "Cisco UCS fabric:EthTargetEp:ifType managed object property"
    ::= { cucsFabricEthTargetEpEntry 8 }

cucsFabricEthTargetEpLicGP OBJECT-TYPE
    SYNTAX       Unsigned64
    MAX-ACCESS   read-only
    STATUS       current
    DESCRIPTION
        "Cisco UCS fabric:EthTargetEp:licGP managed object property"
    ::= { cucsFabricEthTargetEpEntry 9 }

cucsFabricEthTargetEpLicState OBJECT-TYPE
    SYNTAX       CucsLicenseState
    MAX-ACCESS   read-only
    STATUS       current
    DESCRIPTION
        "Cisco UCS fabric:EthTargetEp:licState managed object property"
    ::= { cucsFabricEthTargetEpEntry 10 }

cucsFabricEthTargetEpLocale OBJECT-TYPE
    SYNTAX       CucsFabricExternalEpLocale
    MAX-ACCESS   read-only
    STATUS       current
    DESCRIPTION
        "Cisco UCS fabric:EthTargetEp:locale managed object property"
    ::= { cucsFabricEthTargetEpEntry 11 }

cucsFabricEthTargetEpMacAddress OBJECT-TYPE
    SYNTAX       MacAddress
    MAX-ACCESS   read-only
    STATUS       current
    DESCRIPTION
        "Cisco UCS fabric:EthTargetEp:macAddress managed object property"
    ::= { cucsFabricEthTargetEpEntry 12 }

cucsFabricEthTargetEpName OBJECT-TYPE
    SYNTAX       SnmpAdminString
    MAX-ACCESS   read-only
    STATUS       current
    DESCRIPTION
        "Cisco UCS fabric:EthTargetEp:name managed object property"
    ::= { cucsFabricEthTargetEpEntry 13 }

cucsFabricEthTargetEpPeerDn OBJECT-TYPE
    SYNTAX       SnmpAdminString
    MAX-ACCESS   read-only
    STATUS       current
    DESCRIPTION
        "Cisco UCS fabric:EthTargetEp:peerDn managed object property"
    ::= { cucsFabricEthTargetEpEntry 14 }

cucsFabricEthTargetEpPeerPortId OBJECT-TYPE
    SYNTAX       Gauge32
    MAX-ACCESS   read-only
    STATUS       current
    DESCRIPTION
        "Cisco UCS fabric:EthTargetEp:peerPortId managed object property"
    ::= { cucsFabricEthTargetEpEntry 15 }

cucsFabricEthTargetEpPeerSlotId OBJECT-TYPE
    SYNTAX       Gauge32
    MAX-ACCESS   read-only
    STATUS       current
    DESCRIPTION
        "Cisco UCS fabric:EthTargetEp:peerSlotId managed object property"
    ::= { cucsFabricEthTargetEpEntry 16 }

cucsFabricEthTargetEpPortId OBJECT-TYPE
    SYNTAX       CucsFabricPIoEpPortId
    MAX-ACCESS   read-only
    STATUS       current
    DESCRIPTION
        "Cisco UCS fabric:EthTargetEp:portId managed object property"
    ::= { cucsFabricEthTargetEpEntry 17 }

cucsFabricEthTargetEpSlotId OBJECT-TYPE
    SYNTAX       CucsFabricPIoEpSlotId
    MAX-ACCESS   read-only
    STATUS       current
    DESCRIPTION
        "Cisco UCS fabric:EthTargetEp:slotId managed object property"
    ::= { cucsFabricEthTargetEpEntry 18 }

cucsFabricEthTargetEpSwitchId OBJECT-TYPE
    SYNTAX       CucsNetworkSwitchId
    MAX-ACCESS   read-only
    STATUS       current
    DESCRIPTION
        "Cisco UCS fabric:EthTargetEp:switchId managed object property"
    ::= { cucsFabricEthTargetEpEntry 19 }

cucsFabricEthTargetEpTransport OBJECT-TYPE
    SYNTAX       CucsFabricEthTargetEpTransport
    MAX-ACCESS   read-only
    STATUS       current
    DESCRIPTION
        "Cisco UCS fabric:EthTargetEp:transport managed object property"
    ::= { cucsFabricEthTargetEpEntry 20 }

cucsFabricEthTargetEpType OBJECT-TYPE
    SYNTAX       CucsFabricTargetEpType
    MAX-ACCESS   read-only
    STATUS       current
    DESCRIPTION
        "Cisco UCS fabric:EthTargetEp:type managed object property"
    ::= { cucsFabricEthTargetEpEntry 21 }

cucsFabricEthTargetEpPeerChassisId OBJECT-TYPE
    SYNTAX       Gauge32
    MAX-ACCESS   read-only
    STATUS       current
    DESCRIPTION
        "Cisco UCS fabric:EthTargetEp:peerChassisId managed
        object property"
    ::= { cucsFabricEthTargetEpEntry 22 }

cucsFabricEthTargetEpFltAggr OBJECT-TYPE
    SYNTAX       Unsigned64
    MAX-ACCESS   read-only
    STATUS       current
    DESCRIPTION
        "Cisco UCS fabric:EthTargetEp:fltAggr managed object property"
    ::= { cucsFabricEthTargetEpEntry 23 }

cucsFabricEthVlanPcTable OBJECT-TYPE
    SYNTAX           SEQUENCE OF CucsFabricEthVlanPcEntry
    MAX-ACCESS       not-accessible
    STATUS           current
    DESCRIPTION
        "Cisco UCS fabric:EthVlanPc managed object table"
    ::= { cucsFabricObjects 69 }

cucsFabricEthVlanPcEntry OBJECT-TYPE
    SYNTAX           CucsFabricEthVlanPcEntry
    MAX-ACCESS       not-accessible
    STATUS           current
    DESCRIPTION
        "Entry for the cucsFabricEthVlanPcTable table."
    INDEX { cucsFabricEthVlanPcInstanceId }
    ::= { cucsFabricEthVlanPcTable 1 }

CucsFabricEthVlanPcEntry ::= SEQUENCE {
    cucsFabricEthVlanPcInstanceId                                    CucsManagedObjectId,
    cucsFabricEthVlanPcDn                                            CucsManagedObjectDn,
    cucsFabricEthVlanPcRn                                            SnmpAdminString,
    cucsFabricEthVlanPcAdminSpeed                                    CucsPortEthSpeed,
    cucsFabricEthVlanPcAdminState                                    CucsFabricAdminState,
    cucsFabricEthVlanPcEpDn                                          SnmpAdminString,
    cucsFabricEthVlanPcFltAggr                                       Unsigned64,
    cucsFabricEthVlanPcIfRole                                        CucsFabricEstcPcIfRole,
    cucsFabricEthVlanPcIfType                                        CucsFabricCIoEpIfType,
    cucsFabricEthVlanPcIsNative                                      TruthValue,
    cucsFabricEthVlanPcLocale                                        CucsFabricExternalPcLocale,
    cucsFabricEthVlanPcName                                          SnmpAdminString,
    cucsFabricEthVlanPcOperSpeed                                     CucsPortEthSpeed,
    cucsFabricEthVlanPcOperState                                     CucsNetworkPortOperState,
    cucsFabricEthVlanPcPeerDn                                        SnmpAdminString,
    cucsFabricEthVlanPcPortId                                        Gauge32,
    cucsFabricEthVlanPcStateQual                                     SnmpAdminString,
    cucsFabricEthVlanPcSwitchId                                      CucsNetworkSwitchId,
    cucsFabricEthVlanPcTransport                                     CucsFabricEthVlanPcTransport,
    cucsFabricEthVlanPcType                                          CucsFabricEstcPcType
}

cucsFabricEthVlanPcInstanceId OBJECT-TYPE
    SYNTAX       CucsManagedObjectId
    MAX-ACCESS   not-accessible
    STATUS       current
    DESCRIPTION
        "Instance identifier of the managed object."
    ::= { cucsFabricEthVlanPcEntry 1 }

cucsFabricEthVlanPcDn OBJECT-TYPE
    SYNTAX       CucsManagedObjectDn
    MAX-ACCESS   read-only
    STATUS       current
    DESCRIPTION
        "Cisco UCS fabric:EthVlanPc:dn managed object property"
    ::= { cucsFabricEthVlanPcEntry 2 }

cucsFabricEthVlanPcRn OBJECT-TYPE
    SYNTAX       SnmpAdminString
    MAX-ACCESS   read-only
    STATUS       current
    DESCRIPTION
        "Cisco UCS fabric:EthVlanPc:rn managed object property"
    ::= { cucsFabricEthVlanPcEntry 3 }

cucsFabricEthVlanPcAdminSpeed OBJECT-TYPE
    SYNTAX       CucsPortEthSpeed
    MAX-ACCESS   read-only
    STATUS       current
    DESCRIPTION
        "Cisco UCS fabric:EthVlanPc:adminSpeed managed object property"
    ::= { cucsFabricEthVlanPcEntry 4 }

cucsFabricEthVlanPcAdminState OBJECT-TYPE
    SYNTAX       CucsFabricAdminState
    MAX-ACCESS   read-only
    STATUS       current
    DESCRIPTION
        "Cisco UCS fabric:EthVlanPc:adminState managed object property"
    ::= { cucsFabricEthVlanPcEntry 5 }

cucsFabricEthVlanPcEpDn OBJECT-TYPE
    SYNTAX       SnmpAdminString
    MAX-ACCESS   read-only
    STATUS       current
    DESCRIPTION
        "Cisco UCS fabric:EthVlanPc:epDn managed object property"
    ::= { cucsFabricEthVlanPcEntry 6 }

cucsFabricEthVlanPcFltAggr OBJECT-TYPE
    SYNTAX       Unsigned64
    MAX-ACCESS   read-only
    STATUS       current
    DESCRIPTION
        "Cisco UCS fabric:EthVlanPc:fltAggr managed object property"
    ::= { cucsFabricEthVlanPcEntry 7 }

cucsFabricEthVlanPcIfRole OBJECT-TYPE
    SYNTAX       CucsFabricEstcPcIfRole
    MAX-ACCESS   read-only
    STATUS       current
    DESCRIPTION
        "Cisco UCS fabric:EthVlanPc:ifRole managed object property"
    ::= { cucsFabricEthVlanPcEntry 8 }

cucsFabricEthVlanPcIfType OBJECT-TYPE
    SYNTAX       CucsFabricCIoEpIfType
    MAX-ACCESS   read-only
    STATUS       current
    DESCRIPTION
        "Cisco UCS fabric:EthVlanPc:ifType managed object property"
    ::= { cucsFabricEthVlanPcEntry 9 }

cucsFabricEthVlanPcIsNative OBJECT-TYPE
    SYNTAX       TruthValue
    MAX-ACCESS   read-only
    STATUS       current
    DESCRIPTION
        "Cisco UCS fabric:EthVlanPc:isNative managed object property"
    ::= { cucsFabricEthVlanPcEntry 10 }

cucsFabricEthVlanPcLocale OBJECT-TYPE
    SYNTAX       CucsFabricExternalPcLocale
    MAX-ACCESS   read-only
    STATUS       current
    DESCRIPTION
        "Cisco UCS fabric:EthVlanPc:locale managed object property"
    ::= { cucsFabricEthVlanPcEntry 11 }

cucsFabricEthVlanPcName OBJECT-TYPE
    SYNTAX       SnmpAdminString
    MAX-ACCESS   read-only
    STATUS       current
    DESCRIPTION
        "Cisco UCS fabric:EthVlanPc:name managed object property"
    ::= { cucsFabricEthVlanPcEntry 12 }

cucsFabricEthVlanPcOperSpeed OBJECT-TYPE
    SYNTAX       CucsPortEthSpeed
    MAX-ACCESS   read-only
    STATUS       current
    DESCRIPTION
        "Cisco UCS fabric:EthVlanPc:operSpeed managed object property"
    ::= { cucsFabricEthVlanPcEntry 13 }

cucsFabricEthVlanPcOperState OBJECT-TYPE
    SYNTAX       CucsNetworkPortOperState
    MAX-ACCESS   read-only
    STATUS       current
    DESCRIPTION
        "Cisco UCS fabric:EthVlanPc:operState managed object property"
    ::= { cucsFabricEthVlanPcEntry 14 }

cucsFabricEthVlanPcPeerDn OBJECT-TYPE
    SYNTAX       SnmpAdminString
    MAX-ACCESS   read-only
    STATUS       current
    DESCRIPTION
        "Cisco UCS fabric:EthVlanPc:peerDn managed object property"
    ::= { cucsFabricEthVlanPcEntry 15 }

cucsFabricEthVlanPcPortId OBJECT-TYPE
    SYNTAX       Gauge32
    MAX-ACCESS   read-only
    STATUS       current
    DESCRIPTION
        "Cisco UCS fabric:EthVlanPc:portId managed object property"
    ::= { cucsFabricEthVlanPcEntry 16 }

cucsFabricEthVlanPcStateQual OBJECT-TYPE
    SYNTAX       SnmpAdminString
    MAX-ACCESS   read-only
    STATUS       current
    DESCRIPTION
        "Cisco UCS fabric:EthVlanPc:stateQual managed object property"
    ::= { cucsFabricEthVlanPcEntry 17 }

cucsFabricEthVlanPcSwitchId OBJECT-TYPE
    SYNTAX       CucsNetworkSwitchId
    MAX-ACCESS   read-only
    STATUS       current
    DESCRIPTION
        "Cisco UCS fabric:EthVlanPc:switchId managed object property"
    ::= { cucsFabricEthVlanPcEntry 18 }

cucsFabricEthVlanPcTransport OBJECT-TYPE
    SYNTAX       CucsFabricEthVlanPcTransport
    MAX-ACCESS   read-only
    STATUS       current
    DESCRIPTION
        "Cisco UCS fabric:EthVlanPc:transport managed object property"
    ::= { cucsFabricEthVlanPcEntry 19 }

cucsFabricEthVlanPcType OBJECT-TYPE
    SYNTAX       CucsFabricEstcPcType
    MAX-ACCESS   read-only
    STATUS       current
    DESCRIPTION
        "Cisco UCS fabric:EthVlanPc:type managed object property"
    ::= { cucsFabricEthVlanPcEntry 20 }

cucsFabricEthVlanPortEpTable OBJECT-TYPE
    SYNTAX           SEQUENCE OF CucsFabricEthVlanPortEpEntry
    MAX-ACCESS       not-accessible
    STATUS           current
    DESCRIPTION
        "Cisco UCS fabric:EthVlanPortEp managed object table"
    ::= { cucsFabricObjects 24 }

cucsFabricEthVlanPortEpEntry OBJECT-TYPE
    SYNTAX           CucsFabricEthVlanPortEpEntry
    MAX-ACCESS       not-accessible
    STATUS           current
    DESCRIPTION
        "Entry for the cucsFabricEthVlanPortEpTable table."
    INDEX { cucsFabricEthVlanPortEpInstanceId }
    ::= { cucsFabricEthVlanPortEpTable 1 }

CucsFabricEthVlanPortEpEntry ::= SEQUENCE {
    cucsFabricEthVlanPortEpInstanceId                                CucsManagedObjectId,
    cucsFabricEthVlanPortEpDn                                        CucsManagedObjectDn,
    cucsFabricEthVlanPortEpRn                                        SnmpAdminString,
    cucsFabricEthVlanPortEpAdminState                                CucsFabricExternalEpAdminState,
    cucsFabricEthVlanPortEpChassisId                                 Gauge32,
    cucsFabricEthVlanPortEpEpDn                                      SnmpAdminString,
    cucsFabricEthVlanPortEpIfRole                                    CucsFabricLanEpIfRole,
    cucsFabricEthVlanPortEpIfType                                    CucsFabricPIoEpIfType,
    cucsFabricEthVlanPortEpIsNative                                  TruthValue,
    cucsFabricEthVlanPortEpLicGP                                     Unsigned64,
    cucsFabricEthVlanPortEpLicState                                  CucsLicenseState,
    cucsFabricEthVlanPortEpLocale                                    CucsFabricExternalEpLocale,
    cucsFabricEthVlanPortEpName                                      SnmpAdminString,
    cucsFabricEthVlanPortEpPeerDn                                    SnmpAdminString,
    cucsFabricEthVlanPortEpPeerPortId                                Gauge32,
    cucsFabricEthVlanPortEpPeerSlotId                                Gauge32,
    cucsFabricEthVlanPortEpPortId                                    Gauge32,
    cucsFabricEthVlanPortEpSlotId                                    Gauge32,
    cucsFabricEthVlanPortEpSwitchId                                  CucsNetworkSwitchId,
    cucsFabricEthVlanPortEpTransport                                 CucsFabricAEthLanEpTransport,
    cucsFabricEthVlanPortEpType                                      CucsFabricLanEpType,
    cucsFabricEthVlanPortEpPeerChassisId                             Gauge32,
    cucsFabricEthVlanPortEpFltAggr                                   Unsigned64
}

cucsFabricEthVlanPortEpInstanceId OBJECT-TYPE
    SYNTAX       CucsManagedObjectId
    MAX-ACCESS   not-accessible
    STATUS       current
    DESCRIPTION
        "Instance identifier of the managed object."
    ::= { cucsFabricEthVlanPortEpEntry 1 }

cucsFabricEthVlanPortEpDn OBJECT-TYPE
    SYNTAX       CucsManagedObjectDn
    MAX-ACCESS   read-only
    STATUS       current
    DESCRIPTION
        "Cisco UCS fabric:EthVlanPortEp:dn managed object property"
    ::= { cucsFabricEthVlanPortEpEntry 2 }

cucsFabricEthVlanPortEpRn OBJECT-TYPE
    SYNTAX       SnmpAdminString
    MAX-ACCESS   read-only
    STATUS       current
    DESCRIPTION
        "Cisco UCS fabric:EthVlanPortEp:rn managed object property"
    ::= { cucsFabricEthVlanPortEpEntry 3 }

cucsFabricEthVlanPortEpAdminState OBJECT-TYPE
    SYNTAX       CucsFabricExternalEpAdminState
    MAX-ACCESS   read-only
    STATUS       current
    DESCRIPTION
        "Cisco UCS fabric:EthVlanPortEp:adminState managed
        object property"
    ::= { cucsFabricEthVlanPortEpEntry 4 }

cucsFabricEthVlanPortEpChassisId OBJECT-TYPE
    SYNTAX       Gauge32
    MAX-ACCESS   read-only
    STATUS       current
    DESCRIPTION
        "Cisco UCS fabric:EthVlanPortEp:chassisId managed object property"
    ::= { cucsFabricEthVlanPortEpEntry 5 }

cucsFabricEthVlanPortEpEpDn OBJECT-TYPE
    SYNTAX       SnmpAdminString
    MAX-ACCESS   read-only
    STATUS       current
    DESCRIPTION
        "Cisco UCS fabric:EthVlanPortEp:epDn managed object property"
    ::= { cucsFabricEthVlanPortEpEntry 6 }

cucsFabricEthVlanPortEpIfRole OBJECT-TYPE
    SYNTAX       CucsFabricLanEpIfRole
    MAX-ACCESS   read-only
    STATUS       current
    DESCRIPTION
        "Cisco UCS fabric:EthVlanPortEp:ifRole managed object property"
    ::= { cucsFabricEthVlanPortEpEntry 7 }

cucsFabricEthVlanPortEpIfType OBJECT-TYPE
    SYNTAX       CucsFabricPIoEpIfType
    MAX-ACCESS   read-only
    STATUS       current
    DESCRIPTION
        "Cisco UCS fabric:EthVlanPortEp:ifType managed object property"
    ::= { cucsFabricEthVlanPortEpEntry 8 }

cucsFabricEthVlanPortEpIsNative OBJECT-TYPE
    SYNTAX       TruthValue
    MAX-ACCESS   read-only
    STATUS       current
    DESCRIPTION
        "Cisco UCS fabric:EthVlanPortEp:isNative managed object property"
    ::= { cucsFabricEthVlanPortEpEntry 9 }

cucsFabricEthVlanPortEpLicGP OBJECT-TYPE
    SYNTAX       Unsigned64
    MAX-ACCESS   read-only
    STATUS       current
    DESCRIPTION
        "Cisco UCS fabric:EthVlanPortEp:licGP managed object property"
    ::= { cucsFabricEthVlanPortEpEntry 10 }

cucsFabricEthVlanPortEpLicState OBJECT-TYPE
    SYNTAX       CucsLicenseState
    MAX-ACCESS   read-only
    STATUS       current
    DESCRIPTION
        "Cisco UCS fabric:EthVlanPortEp:licState managed object property"
    ::= { cucsFabricEthVlanPortEpEntry 11 }

cucsFabricEthVlanPortEpLocale OBJECT-TYPE
    SYNTAX       CucsFabricExternalEpLocale
    MAX-ACCESS   read-only
    STATUS       current
    DESCRIPTION
        "Cisco UCS fabric:EthVlanPortEp:locale managed object property"
    ::= { cucsFabricEthVlanPortEpEntry 12 }

cucsFabricEthVlanPortEpName OBJECT-TYPE
    SYNTAX       SnmpAdminString
    MAX-ACCESS   read-only
    STATUS       current
    DESCRIPTION
        "Cisco UCS fabric:EthVlanPortEp:name managed object property"
    ::= { cucsFabricEthVlanPortEpEntry 13 }

cucsFabricEthVlanPortEpPeerDn OBJECT-TYPE
    SYNTAX       SnmpAdminString
    MAX-ACCESS   read-only
    STATUS       current
    DESCRIPTION
        "Cisco UCS fabric:EthVlanPortEp:peerDn managed object property"
    ::= { cucsFabricEthVlanPortEpEntry 14 }

cucsFabricEthVlanPortEpPeerPortId OBJECT-TYPE
    SYNTAX       Gauge32
    MAX-ACCESS   read-only
    STATUS       current
    DESCRIPTION
        "Cisco UCS fabric:EthVlanPortEp:peerPortId managed
        object property"
    ::= { cucsFabricEthVlanPortEpEntry 15 }

cucsFabricEthVlanPortEpPeerSlotId OBJECT-TYPE
    SYNTAX       Gauge32
    MAX-ACCESS   read-only
    STATUS       current
    DESCRIPTION
        "Cisco UCS fabric:EthVlanPortEp:peerSlotId managed
        object property"
    ::= { cucsFabricEthVlanPortEpEntry 16 }

cucsFabricEthVlanPortEpPortId OBJECT-TYPE
    SYNTAX       Gauge32
    MAX-ACCESS   read-only
    STATUS       current
    DESCRIPTION
        "Cisco UCS fabric:EthVlanPortEp:portId managed object property"
    ::= { cucsFabricEthVlanPortEpEntry 17 }

cucsFabricEthVlanPortEpSlotId OBJECT-TYPE
    SYNTAX       Gauge32
    MAX-ACCESS   read-only
    STATUS       current
    DESCRIPTION
        "Cisco UCS fabric:EthVlanPortEp:slotId managed object property"
    ::= { cucsFabricEthVlanPortEpEntry 18 }

cucsFabricEthVlanPortEpSwitchId OBJECT-TYPE
    SYNTAX       CucsNetworkSwitchId
    MAX-ACCESS   read-only
    STATUS       current
    DESCRIPTION
        "Cisco UCS fabric:EthVlanPortEp:switchId managed object property"
    ::= { cucsFabricEthVlanPortEpEntry 19 }

cucsFabricEthVlanPortEpTransport OBJECT-TYPE
    SYNTAX       CucsFabricAEthLanEpTransport
    MAX-ACCESS   read-only
    STATUS       current
    DESCRIPTION
        "Cisco UCS fabric:EthVlanPortEp:transport managed object property"
    ::= { cucsFabricEthVlanPortEpEntry 20 }

cucsFabricEthVlanPortEpType OBJECT-TYPE
    SYNTAX       CucsFabricLanEpType
    MAX-ACCESS   read-only
    STATUS       current
    DESCRIPTION
        "Cisco UCS fabric:EthVlanPortEp:type managed object property"
    ::= { cucsFabricEthVlanPortEpEntry 21 }

cucsFabricEthVlanPortEpPeerChassisId OBJECT-TYPE
    SYNTAX       Gauge32
    MAX-ACCESS   read-only
    STATUS       current
    DESCRIPTION
        "Cisco UCS fabric:EthVlanPortEp:peerChassisId managed
        object property"
    ::= { cucsFabricEthVlanPortEpEntry 22 }

cucsFabricEthVlanPortEpFltAggr OBJECT-TYPE
    SYNTAX       Unsigned64
    MAX-ACCESS   read-only
    STATUS       current
    DESCRIPTION
        "Cisco UCS fabric:EthVlanPortEp:fltAggr managed object property"
    ::= { cucsFabricEthVlanPortEpEntry 23 }

cucsFabricFcEstcTable OBJECT-TYPE
    SYNTAX           SEQUENCE OF CucsFabricFcEstcEntry
    MAX-ACCESS       not-accessible
    STATUS           current
    DESCRIPTION
        "Cisco UCS fabric:FcEstc managed object table"
    ::= { cucsFabricObjects 25 }

cucsFabricFcEstcEntry OBJECT-TYPE
    SYNTAX           CucsFabricFcEstcEntry
    MAX-ACCESS       not-accessible
    STATUS           current
    DESCRIPTION
        "Entry for the cucsFabricFcEstcTable table."
    INDEX { cucsFabricFcEstcInstanceId }
    ::= { cucsFabricFcEstcTable 1 }

CucsFabricFcEstcEntry ::= SEQUENCE {
    cucsFabricFcEstcInstanceId                                       CucsManagedObjectId,
    cucsFabricFcEstcDn                                               CucsManagedObjectDn,
    cucsFabricFcEstcRn                                               SnmpAdminString,
    cucsFabricFcEstcId                                               CucsNetworkSwitchId,
    cucsFabricFcEstcLocale                                           CucsFabricExternalLocale,
    cucsFabricFcEstcName                                             SnmpAdminString,
    cucsFabricFcEstcTransport                                        CucsFabricFcEstcTransport,
    cucsFabricFcEstcType                                             CucsFabricFcEstcType
}

cucsFabricFcEstcInstanceId OBJECT-TYPE
    SYNTAX       CucsManagedObjectId
    MAX-ACCESS   not-accessible
    STATUS       current
    DESCRIPTION
        "Instance identifier of the managed object."
    ::= { cucsFabricFcEstcEntry 1 }

cucsFabricFcEstcDn OBJECT-TYPE
    SYNTAX       CucsManagedObjectDn
    MAX-ACCESS   read-only
    STATUS       current
    DESCRIPTION
        "Cisco UCS fabric:FcEstc:dn managed object property"
    ::= { cucsFabricFcEstcEntry 2 }

cucsFabricFcEstcRn OBJECT-TYPE
    SYNTAX       SnmpAdminString
    MAX-ACCESS   read-only
    STATUS       current
    DESCRIPTION
        "Cisco UCS fabric:FcEstc:rn managed object property"
    ::= { cucsFabricFcEstcEntry 3 }

cucsFabricFcEstcId OBJECT-TYPE
    SYNTAX       CucsNetworkSwitchId
    MAX-ACCESS   read-only
    STATUS       current
    DESCRIPTION
        "Cisco UCS fabric:FcEstc:id managed object property"
    ::= { cucsFabricFcEstcEntry 4 }

cucsFabricFcEstcLocale OBJECT-TYPE
    SYNTAX       CucsFabricExternalLocale
    MAX-ACCESS   read-only
    STATUS       current
    DESCRIPTION
        "Cisco UCS fabric:FcEstc:locale managed object property"
    ::= { cucsFabricFcEstcEntry 5 }

cucsFabricFcEstcName OBJECT-TYPE
    SYNTAX       SnmpAdminString
    MAX-ACCESS   read-only
    STATUS       current
    DESCRIPTION
        "Cisco UCS fabric:FcEstc:name managed object property"
    ::= { cucsFabricFcEstcEntry 6 }

cucsFabricFcEstcTransport OBJECT-TYPE
    SYNTAX       CucsFabricFcEstcTransport
    MAX-ACCESS   read-only
    STATUS       current
    DESCRIPTION
        "Cisco UCS fabric:FcEstc:transport managed object property"
    ::= { cucsFabricFcEstcEntry 7 }

cucsFabricFcEstcType OBJECT-TYPE
    SYNTAX       CucsFabricFcEstcType
    MAX-ACCESS   read-only
    STATUS       current
    DESCRIPTION
        "Cisco UCS fabric:FcEstc:type managed object property"
    ::= { cucsFabricFcEstcEntry 8 }

cucsFabricFcEstcCloudTable OBJECT-TYPE
    SYNTAX           SEQUENCE OF CucsFabricFcEstcCloudEntry
    MAX-ACCESS       not-accessible
    STATUS           current
    DESCRIPTION
        "Cisco UCS fabric:FcEstcCloud managed object table"
    ::= { cucsFabricObjects 26 }

cucsFabricFcEstcCloudEntry OBJECT-TYPE
    SYNTAX           CucsFabricFcEstcCloudEntry
    MAX-ACCESS       not-accessible
    STATUS           current
    DESCRIPTION
        "Entry for the cucsFabricFcEstcCloudTable table."
    INDEX { cucsFabricFcEstcCloudInstanceId }
    ::= { cucsFabricFcEstcCloudTable 1 }

CucsFabricFcEstcCloudEntry ::= SEQUENCE {
    cucsFabricFcEstcCloudInstanceId                                  CucsManagedObjectId,
    cucsFabricFcEstcCloudDn                                          CucsManagedObjectDn,
    cucsFabricFcEstcCloudRn                                          SnmpAdminString
}

cucsFabricFcEstcCloudInstanceId OBJECT-TYPE
    SYNTAX       CucsManagedObjectId
    MAX-ACCESS   not-accessible
    STATUS       current
    DESCRIPTION
        "Instance identifier of the managed object."
    ::= { cucsFabricFcEstcCloudEntry 1 }

cucsFabricFcEstcCloudDn OBJECT-TYPE
    SYNTAX       CucsManagedObjectDn
    MAX-ACCESS   read-only
    STATUS       current
    DESCRIPTION
        "Cisco UCS fabric:FcEstcCloud:dn managed object property"
    ::= { cucsFabricFcEstcCloudEntry 2 }

cucsFabricFcEstcCloudRn OBJECT-TYPE
    SYNTAX       SnmpAdminString
    MAX-ACCESS   read-only
    STATUS       current
    DESCRIPTION
        "Cisco UCS fabric:FcEstcCloud:rn managed object property"
    ::= { cucsFabricFcEstcCloudEntry 3 }

cucsFabricFcEstcEpTable OBJECT-TYPE
    SYNTAX           SEQUENCE OF CucsFabricFcEstcEpEntry
    MAX-ACCESS       not-accessible
    STATUS           current
    DESCRIPTION
        "Cisco UCS fabric:FcEstcEp managed object table"
    ::= { cucsFabricObjects 27 }

cucsFabricFcEstcEpEntry OBJECT-TYPE
    SYNTAX           CucsFabricFcEstcEpEntry
    MAX-ACCESS       not-accessible
    STATUS           current
    DESCRIPTION
        "Entry for the cucsFabricFcEstcEpTable table."
    INDEX { cucsFabricFcEstcEpInstanceId }
    ::= { cucsFabricFcEstcEpTable 1 }

CucsFabricFcEstcEpEntry ::= SEQUENCE {
    cucsFabricFcEstcEpInstanceId                                     CucsManagedObjectId,
    cucsFabricFcEstcEpDn                                             CucsManagedObjectDn,
    cucsFabricFcEstcEpRn                                             SnmpAdminString,
    cucsFabricFcEstcEpAdminState                                     CucsFabricExternalEpAdminState,
    cucsFabricFcEstcEpChassisId                                      Gauge32,
    cucsFabricFcEstcEpConfigState                                    CucsFabricConfigState,
    cucsFabricFcEstcEpEpDn                                           SnmpAdminString,
    cucsFabricFcEstcEpIfRole                                         CucsFabricEstcEpIfRole,
    cucsFabricFcEstcEpIfType                                         CucsFabricPIoEpIfType,
    cucsFabricFcEstcEpLicGP                                          Unsigned64,
    cucsFabricFcEstcEpLicState                                       CucsLicenseState,
    cucsFabricFcEstcEpLocale                                         CucsFabricExternalEpLocale,
    cucsFabricFcEstcEpName                                           SnmpAdminString,
    cucsFabricFcEstcEpPeerDn                                         SnmpAdminString,
    cucsFabricFcEstcEpPeerPortId                                     Gauge32,
    cucsFabricFcEstcEpPeerSlotId                                     Gauge32,
    cucsFabricFcEstcEpPortId                                         CucsFabricFcEstcEpPortId,
    cucsFabricFcEstcEpSlotId                                         CucsFabricFcEstcEpSlotId,
    cucsFabricFcEstcEpSwitchId                                       CucsNetworkSwitchId,
    cucsFabricFcEstcEpTransport                                      CucsFabricAFcEstcEpTransport,
    cucsFabricFcEstcEpType                                           CucsFabricAFcEstcEpType,
    cucsFabricFcEstcEpUsrLbl                                         SnmpAdminString,
    cucsFabricFcEstcEpPeerChassisId                                  Gauge32,
    cucsFabricFcEstcEpFltAggr                                        Unsigned64
}

cucsFabricFcEstcEpInstanceId OBJECT-TYPE
    SYNTAX       CucsManagedObjectId
    MAX-ACCESS   not-accessible
    STATUS       current
    DESCRIPTION
        "Instance identifier of the managed object."
    ::= { cucsFabricFcEstcEpEntry 1 }

cucsFabricFcEstcEpDn OBJECT-TYPE
    SYNTAX       CucsManagedObjectDn
    MAX-ACCESS   read-only
    STATUS       current
    DESCRIPTION
        "Cisco UCS fabric:FcEstcEp:dn managed object property"
    ::= { cucsFabricFcEstcEpEntry 2 }

cucsFabricFcEstcEpRn OBJECT-TYPE
    SYNTAX       SnmpAdminString
    MAX-ACCESS   read-only
    STATUS       current
    DESCRIPTION
        "Cisco UCS fabric:FcEstcEp:rn managed object property"
    ::= { cucsFabricFcEstcEpEntry 3 }

cucsFabricFcEstcEpAdminState OBJECT-TYPE
    SYNTAX       CucsFabricExternalEpAdminState
    MAX-ACCESS   read-only
    STATUS       current
    DESCRIPTION
        "Cisco UCS fabric:FcEstcEp:adminState managed object property"
    ::= { cucsFabricFcEstcEpEntry 4 }

cucsFabricFcEstcEpChassisId OBJECT-TYPE
    SYNTAX       Gauge32
    MAX-ACCESS   read-only
    STATUS       current
    DESCRIPTION
        "Cisco UCS fabric:FcEstcEp:chassisId managed object property"
    ::= { cucsFabricFcEstcEpEntry 5 }

cucsFabricFcEstcEpConfigState OBJECT-TYPE
    SYNTAX       CucsFabricConfigState
    MAX-ACCESS   read-only
    STATUS       current
    DESCRIPTION
        "Cisco UCS fabric:FcEstcEp:configState managed object property"
    ::= { cucsFabricFcEstcEpEntry 6 }

cucsFabricFcEstcEpEpDn OBJECT-TYPE
    SYNTAX       SnmpAdminString
    MAX-ACCESS   read-only
    STATUS       current
    DESCRIPTION
        "Cisco UCS fabric:FcEstcEp:epDn managed object property"
    ::= { cucsFabricFcEstcEpEntry 7 }

cucsFabricFcEstcEpIfRole OBJECT-TYPE
    SYNTAX       CucsFabricEstcEpIfRole
    MAX-ACCESS   read-only
    STATUS       current
    DESCRIPTION
        "Cisco UCS fabric:FcEstcEp:ifRole managed object property"
    ::= { cucsFabricFcEstcEpEntry 8 }

cucsFabricFcEstcEpIfType OBJECT-TYPE
    SYNTAX       CucsFabricPIoEpIfType
    MAX-ACCESS   read-only
    STATUS       current
    DESCRIPTION
        "Cisco UCS fabric:FcEstcEp:ifType managed object property"
    ::= { cucsFabricFcEstcEpEntry 9 }

cucsFabricFcEstcEpLicGP OBJECT-TYPE
    SYNTAX       Unsigned64
    MAX-ACCESS   read-only
    STATUS       current
    DESCRIPTION
        "Cisco UCS fabric:FcEstcEp:licGP managed object property"
    ::= { cucsFabricFcEstcEpEntry 10 }

cucsFabricFcEstcEpLicState OBJECT-TYPE
    SYNTAX       CucsLicenseState
    MAX-ACCESS   read-only
    STATUS       current
    DESCRIPTION
        "Cisco UCS fabric:FcEstcEp:licState managed object property"
    ::= { cucsFabricFcEstcEpEntry 11 }

cucsFabricFcEstcEpLocale OBJECT-TYPE
    SYNTAX       CucsFabricExternalEpLocale
    MAX-ACCESS   read-only
    STATUS       current
    DESCRIPTION
        "Cisco UCS fabric:FcEstcEp:locale managed object property"
    ::= { cucsFabricFcEstcEpEntry 12 }

cucsFabricFcEstcEpName OBJECT-TYPE
    SYNTAX       SnmpAdminString
    MAX-ACCESS   read-only
    STATUS       current
    DESCRIPTION
        "Cisco UCS fabric:FcEstcEp:name managed object property"
    ::= { cucsFabricFcEstcEpEntry 13 }

cucsFabricFcEstcEpPeerDn OBJECT-TYPE
    SYNTAX       SnmpAdminString
    MAX-ACCESS   read-only
    STATUS       current
    DESCRIPTION
        "Cisco UCS fabric:FcEstcEp:peerDn managed object property"
    ::= { cucsFabricFcEstcEpEntry 14 }

cucsFabricFcEstcEpPeerPortId OBJECT-TYPE
    SYNTAX       Gauge32
    MAX-ACCESS   read-only
    STATUS       current
    DESCRIPTION
        "Cisco UCS fabric:FcEstcEp:peerPortId managed object property"
    ::= { cucsFabricFcEstcEpEntry 15 }

cucsFabricFcEstcEpPeerSlotId OBJECT-TYPE
    SYNTAX       Gauge32
    MAX-ACCESS   read-only
    STATUS       current
    DESCRIPTION
        "Cisco UCS fabric:FcEstcEp:peerSlotId managed object property"
    ::= { cucsFabricFcEstcEpEntry 16 }

cucsFabricFcEstcEpPortId OBJECT-TYPE
    SYNTAX       CucsFabricFcEstcEpPortId
    MAX-ACCESS   read-only
    STATUS       current
    DESCRIPTION
        "Cisco UCS fabric:FcEstcEp:portId managed object property"
    ::= { cucsFabricFcEstcEpEntry 17 }

cucsFabricFcEstcEpSlotId OBJECT-TYPE
    SYNTAX       CucsFabricFcEstcEpSlotId
    MAX-ACCESS   read-only
    STATUS       current
    DESCRIPTION
        "Cisco UCS fabric:FcEstcEp:slotId managed object property"
    ::= { cucsFabricFcEstcEpEntry 18 }

cucsFabricFcEstcEpSwitchId OBJECT-TYPE
    SYNTAX       CucsNetworkSwitchId
    MAX-ACCESS   read-only
    STATUS       current
    DESCRIPTION
        "Cisco UCS fabric:FcEstcEp:switchId managed object property"
    ::= { cucsFabricFcEstcEpEntry 19 }

cucsFabricFcEstcEpTransport OBJECT-TYPE
    SYNTAX       CucsFabricAFcEstcEpTransport
    MAX-ACCESS   read-only
    STATUS       current
    DESCRIPTION
        "Cisco UCS fabric:FcEstcEp:transport managed object property"
    ::= { cucsFabricFcEstcEpEntry 20 }

cucsFabricFcEstcEpType OBJECT-TYPE
    SYNTAX       CucsFabricAFcEstcEpType
    MAX-ACCESS   read-only
    STATUS       current
    DESCRIPTION
        "Cisco UCS fabric:FcEstcEp:type managed object property"
    ::= { cucsFabricFcEstcEpEntry 21 }

cucsFabricFcEstcEpUsrLbl OBJECT-TYPE
    SYNTAX       SnmpAdminString
    MAX-ACCESS   read-only
    STATUS       current
    DESCRIPTION
        "Cisco UCS fabric:FcEstcEp:usrLbl managed object property"
    ::= { cucsFabricFcEstcEpEntry 22 }

cucsFabricFcEstcEpPeerChassisId OBJECT-TYPE
    SYNTAX       Gauge32
    MAX-ACCESS   read-only
    STATUS       current
    DESCRIPTION
        "Cisco UCS fabric:FcEstcEp:peerChassisId managed object property"
    ::= { cucsFabricFcEstcEpEntry 23 }

cucsFabricFcEstcEpFltAggr OBJECT-TYPE
    SYNTAX       Unsigned64
    MAX-ACCESS   read-only
    STATUS       current
    DESCRIPTION
        "Cisco UCS fabric:FcEstcEp:fltAggr managed object property"
    ::= { cucsFabricFcEstcEpEntry 24 }

cucsFabricFcMonTable OBJECT-TYPE
    SYNTAX           SEQUENCE OF CucsFabricFcMonEntry
    MAX-ACCESS       not-accessible
    STATUS           current
    DESCRIPTION
        "Cisco UCS fabric:FcMon managed object table"
    ::= { cucsFabricObjects 28 }

cucsFabricFcMonEntry OBJECT-TYPE
    SYNTAX           CucsFabricFcMonEntry
    MAX-ACCESS       not-accessible
    STATUS           current
    DESCRIPTION
        "Entry for the cucsFabricFcMonTable table."
    INDEX { cucsFabricFcMonInstanceId }
    ::= { cucsFabricFcMonTable 1 }

CucsFabricFcMonEntry ::= SEQUENCE {
    cucsFabricFcMonInstanceId                                        CucsManagedObjectId,
    cucsFabricFcMonDn                                                CucsManagedObjectDn,
    cucsFabricFcMonRn                                                SnmpAdminString,
    cucsFabricFcMonAdminState                                        CucsFabricMonAdminState,
    cucsFabricFcMonId                                                CucsNetworkSwitchId,
    cucsFabricFcMonLocale                                            CucsFabricExternalLocale,
    cucsFabricFcMonName                                              SnmpAdminString,
    cucsFabricFcMonSession                                           Gauge32,
    cucsFabricFcMonTransport                                         CucsFabricFcMonTransport,
    cucsFabricFcMonType                                              CucsFabricFcMonType,
    cucsFabricFcMonConfigFailReason                                  SnmpAdminString,
    cucsFabricFcMonIsConfigSuccess                                   TruthValue,
    cucsFabricFcMonOperState                                         CucsFabricMonOperState,
    cucsFabricFcMonOperStateReason                                   CucsFabricMonOperStateReason,
    cucsFabricFcMonPeerDn                                            SnmpAdminString
}

cucsFabricFcMonInstanceId OBJECT-TYPE
    SYNTAX       CucsManagedObjectId
    MAX-ACCESS   not-accessible
    STATUS       current
    DESCRIPTION
        "Instance identifier of the managed object."
    ::= { cucsFabricFcMonEntry 1 }

cucsFabricFcMonDn OBJECT-TYPE
    SYNTAX       CucsManagedObjectDn
    MAX-ACCESS   read-only
    STATUS       current
    DESCRIPTION
        "Cisco UCS fabric:FcMon:dn managed object property"
    ::= { cucsFabricFcMonEntry 2 }

cucsFabricFcMonRn OBJECT-TYPE
    SYNTAX       SnmpAdminString
    MAX-ACCESS   read-only
    STATUS       current
    DESCRIPTION
        "Cisco UCS fabric:FcMon:rn managed object property"
    ::= { cucsFabricFcMonEntry 3 }

cucsFabricFcMonAdminState OBJECT-TYPE
    SYNTAX       CucsFabricMonAdminState
    MAX-ACCESS   read-only
    STATUS       current
    DESCRIPTION
        "Cisco UCS fabric:FcMon:adminState managed object property"
    ::= { cucsFabricFcMonEntry 4 }

cucsFabricFcMonId OBJECT-TYPE
    SYNTAX       CucsNetworkSwitchId
    MAX-ACCESS   read-only
    STATUS       current
    DESCRIPTION
        "Cisco UCS fabric:FcMon:id managed object property"
    ::= { cucsFabricFcMonEntry 5 }

cucsFabricFcMonLocale OBJECT-TYPE
    SYNTAX       CucsFabricExternalLocale
    MAX-ACCESS   read-only
    STATUS       current
    DESCRIPTION
        "Cisco UCS fabric:FcMon:locale managed object property"
    ::= { cucsFabricFcMonEntry 6 }

cucsFabricFcMonName OBJECT-TYPE
    SYNTAX       SnmpAdminString
    MAX-ACCESS   read-only
    STATUS       current
    DESCRIPTION
        "Cisco UCS fabric:FcMon:name managed object property"
    ::= { cucsFabricFcMonEntry 7 }

cucsFabricFcMonSession OBJECT-TYPE
    SYNTAX       Gauge32
    MAX-ACCESS   read-only
    STATUS       current
    DESCRIPTION
        "Cisco UCS fabric:FcMon:session managed object property"
    ::= { cucsFabricFcMonEntry 8 }

cucsFabricFcMonTransport OBJECT-TYPE
    SYNTAX       CucsFabricFcMonTransport
    MAX-ACCESS   read-only
    STATUS       current
    DESCRIPTION
        "Cisco UCS fabric:FcMon:transport managed object property"
    ::= { cucsFabricFcMonEntry 9 }

cucsFabricFcMonType OBJECT-TYPE
    SYNTAX       CucsFabricFcMonType
    MAX-ACCESS   read-only
    STATUS       current
    DESCRIPTION
        "Cisco UCS fabric:FcMon:type managed object property"
    ::= { cucsFabricFcMonEntry 10 }

cucsFabricFcMonConfigFailReason OBJECT-TYPE
    SYNTAX       SnmpAdminString
    MAX-ACCESS   read-only
    STATUS       current
    DESCRIPTION
        "Cisco UCS fabric:FcMon:configFailReason managed object property"
    ::= { cucsFabricFcMonEntry 11 }

cucsFabricFcMonIsConfigSuccess OBJECT-TYPE
    SYNTAX       TruthValue
    MAX-ACCESS   read-only
    STATUS       current
    DESCRIPTION
        "Cisco UCS fabric:FcMon:isConfigSuccess managed object property"
    ::= { cucsFabricFcMonEntry 12 }

cucsFabricFcMonOperState OBJECT-TYPE
    SYNTAX       CucsFabricMonOperState
    MAX-ACCESS   read-only
    STATUS       current
    DESCRIPTION
        "Cisco UCS fabric:FcMon:operState managed object property"
    ::= { cucsFabricFcMonEntry 13 }

cucsFabricFcMonOperStateReason OBJECT-TYPE
    SYNTAX       CucsFabricMonOperStateReason
    MAX-ACCESS   read-only
    STATUS       current
    DESCRIPTION
        "Cisco UCS fabric:FcMon:operStateReason managed object property"
    ::= { cucsFabricFcMonEntry 14 }

cucsFabricFcMonPeerDn OBJECT-TYPE
    SYNTAX       SnmpAdminString
    MAX-ACCESS   read-only
    STATUS       current
    DESCRIPTION
        "Cisco UCS fabric:FcMon:peerDn managed object property"
    ::= { cucsFabricFcMonEntry 15 }

cucsFabricFcMonDestEpTable OBJECT-TYPE
    SYNTAX           SEQUENCE OF CucsFabricFcMonDestEpEntry
    MAX-ACCESS       not-accessible
    STATUS           current
    DESCRIPTION
        "Cisco UCS fabric:FcMonDestEp managed object table"
    ::= { cucsFabricObjects 29 }

cucsFabricFcMonDestEpEntry OBJECT-TYPE
    SYNTAX           CucsFabricFcMonDestEpEntry
    MAX-ACCESS       not-accessible
    STATUS           current
    DESCRIPTION
        "Entry for the cucsFabricFcMonDestEpTable table."
    INDEX { cucsFabricFcMonDestEpInstanceId }
    ::= { cucsFabricFcMonDestEpTable 1 }

CucsFabricFcMonDestEpEntry ::= SEQUENCE {
    cucsFabricFcMonDestEpInstanceId                                  CucsManagedObjectId,
    cucsFabricFcMonDestEpDn                                          CucsManagedObjectDn,
    cucsFabricFcMonDestEpRn                                          SnmpAdminString,
    cucsFabricFcMonDestEpAdminState                                  CucsFabricExternalEpAdminState,
    cucsFabricFcMonDestEpChassisId                                   Gauge32,
    cucsFabricFcMonDestEpEpDn                                        SnmpAdminString,
    cucsFabricFcMonDestEpIfRole                                      CucsFabricFcMonDestEpIfRole,
    cucsFabricFcMonDestEpIfType                                      CucsFabricPIoEpIfType,
    cucsFabricFcMonDestEpLicGP                                       Unsigned64,
    cucsFabricFcMonDestEpLicState                                    CucsLicenseState,
    cucsFabricFcMonDestEpLocale                                      CucsFabricExternalEpLocale,
    cucsFabricFcMonDestEpName                                        SnmpAdminString,
    cucsFabricFcMonDestEpPeerDn                                      SnmpAdminString,
    cucsFabricFcMonDestEpPeerPortId                                  Gauge32,
    cucsFabricFcMonDestEpPeerSlotId                                  Gauge32,
    cucsFabricFcMonDestEpPortId                                      CucsFabricFcMonDestEpPortId,
    cucsFabricFcMonDestEpSlotId                                      CucsFabricFcMonDestEpSlotId,
    cucsFabricFcMonDestEpSwitchId                                    CucsNetworkSwitchId,
    cucsFabricFcMonDestEpTransport                                   CucsNetworkTransport,
    cucsFabricFcMonDestEpType                                        CucsFabricFcMonDestEpType,
    cucsFabricFcMonDestEpPeerChassisId                               Gauge32,
    cucsFabricFcMonDestEpFltAggr                                     Unsigned64
}

cucsFabricFcMonDestEpInstanceId OBJECT-TYPE
    SYNTAX       CucsManagedObjectId
    MAX-ACCESS   not-accessible
    STATUS       current
    DESCRIPTION
        "Instance identifier of the managed object."
    ::= { cucsFabricFcMonDestEpEntry 1 }

cucsFabricFcMonDestEpDn OBJECT-TYPE
    SYNTAX       CucsManagedObjectDn
    MAX-ACCESS   read-only
    STATUS       current
    DESCRIPTION
        "Cisco UCS fabric:FcMonDestEp:dn managed object property"
    ::= { cucsFabricFcMonDestEpEntry 2 }

cucsFabricFcMonDestEpRn OBJECT-TYPE
    SYNTAX       SnmpAdminString
    MAX-ACCESS   read-only
    STATUS       current
    DESCRIPTION
        "Cisco UCS fabric:FcMonDestEp:rn managed object property"
    ::= { cucsFabricFcMonDestEpEntry 3 }

cucsFabricFcMonDestEpAdminState OBJECT-TYPE
    SYNTAX       CucsFabricExternalEpAdminState
    MAX-ACCESS   read-only
    STATUS       current
    DESCRIPTION
        "Cisco UCS fabric:FcMonDestEp:adminState managed object property"
    ::= { cucsFabricFcMonDestEpEntry 4 }

cucsFabricFcMonDestEpChassisId OBJECT-TYPE
    SYNTAX       Gauge32
    MAX-ACCESS   read-only
    STATUS       current
    DESCRIPTION
        "Cisco UCS fabric:FcMonDestEp:chassisId managed object property"
    ::= { cucsFabricFcMonDestEpEntry 5 }

cucsFabricFcMonDestEpEpDn OBJECT-TYPE
    SYNTAX       SnmpAdminString
    MAX-ACCESS   read-only
    STATUS       current
    DESCRIPTION
        "Cisco UCS fabric:FcMonDestEp:epDn managed object property"
    ::= { cucsFabricFcMonDestEpEntry 6 }

cucsFabricFcMonDestEpIfRole OBJECT-TYPE
    SYNTAX       CucsFabricFcMonDestEpIfRole
    MAX-ACCESS   read-only
    STATUS       current
    DESCRIPTION
        "Cisco UCS fabric:FcMonDestEp:ifRole managed object property"
    ::= { cucsFabricFcMonDestEpEntry 7 }

cucsFabricFcMonDestEpIfType OBJECT-TYPE
    SYNTAX       CucsFabricPIoEpIfType
    MAX-ACCESS   read-only
    STATUS       current
    DESCRIPTION
        "Cisco UCS fabric:FcMonDestEp:ifType managed object property"
    ::= { cucsFabricFcMonDestEpEntry 8 }

cucsFabricFcMonDestEpLicGP OBJECT-TYPE
    SYNTAX       Unsigned64
    MAX-ACCESS   read-only
    STATUS       current
    DESCRIPTION
        "Cisco UCS fabric:FcMonDestEp:licGP managed object property"
    ::= { cucsFabricFcMonDestEpEntry 9 }

cucsFabricFcMonDestEpLicState OBJECT-TYPE
    SYNTAX       CucsLicenseState
    MAX-ACCESS   read-only
    STATUS       current
    DESCRIPTION
        "Cisco UCS fabric:FcMonDestEp:licState managed object property"
    ::= { cucsFabricFcMonDestEpEntry 10 }

cucsFabricFcMonDestEpLocale OBJECT-TYPE
    SYNTAX       CucsFabricExternalEpLocale
    MAX-ACCESS   read-only
    STATUS       current
    DESCRIPTION
        "Cisco UCS fabric:FcMonDestEp:locale managed object property"
    ::= { cucsFabricFcMonDestEpEntry 11 }

cucsFabricFcMonDestEpName OBJECT-TYPE
    SYNTAX       SnmpAdminString
    MAX-ACCESS   read-only
    STATUS       current
    DESCRIPTION
        "Cisco UCS fabric:FcMonDestEp:name managed object property"
    ::= { cucsFabricFcMonDestEpEntry 12 }

cucsFabricFcMonDestEpPeerDn OBJECT-TYPE
    SYNTAX       SnmpAdminString
    MAX-ACCESS   read-only
    STATUS       current
    DESCRIPTION
        "Cisco UCS fabric:FcMonDestEp:peerDn managed object property"
    ::= { cucsFabricFcMonDestEpEntry 13 }

cucsFabricFcMonDestEpPeerPortId OBJECT-TYPE
    SYNTAX       Gauge32
    MAX-ACCESS   read-only
    STATUS       current
    DESCRIPTION
        "Cisco UCS fabric:FcMonDestEp:peerPortId managed object property"
    ::= { cucsFabricFcMonDestEpEntry 14 }

cucsFabricFcMonDestEpPeerSlotId OBJECT-TYPE
    SYNTAX       Gauge32
    MAX-ACCESS   read-only
    STATUS       current
    DESCRIPTION
        "Cisco UCS fabric:FcMonDestEp:peerSlotId managed object property"
    ::= { cucsFabricFcMonDestEpEntry 15 }

cucsFabricFcMonDestEpPortId OBJECT-TYPE
    SYNTAX       CucsFabricFcMonDestEpPortId
    MAX-ACCESS   read-only
    STATUS       current
    DESCRIPTION
        "Cisco UCS fabric:FcMonDestEp:portId managed object property"
    ::= { cucsFabricFcMonDestEpEntry 16 }

cucsFabricFcMonDestEpSlotId OBJECT-TYPE
    SYNTAX       CucsFabricFcMonDestEpSlotId
    MAX-ACCESS   read-only
    STATUS       current
    DESCRIPTION
        "Cisco UCS fabric:FcMonDestEp:slotId managed object property"
    ::= { cucsFabricFcMonDestEpEntry 17 }

cucsFabricFcMonDestEpSwitchId OBJECT-TYPE
    SYNTAX       CucsNetworkSwitchId
    MAX-ACCESS   read-only
    STATUS       current
    DESCRIPTION
        "Cisco UCS fabric:FcMonDestEp:switchId managed object property"
    ::= { cucsFabricFcMonDestEpEntry 18 }

cucsFabricFcMonDestEpTransport OBJECT-TYPE
    SYNTAX       CucsNetworkTransport
    MAX-ACCESS   read-only
    STATUS       current
    DESCRIPTION
        "Cisco UCS fabric:FcMonDestEp:transport managed object property"
    ::= { cucsFabricFcMonDestEpEntry 19 }

cucsFabricFcMonDestEpType OBJECT-TYPE
    SYNTAX       CucsFabricFcMonDestEpType
    MAX-ACCESS   read-only
    STATUS       current
    DESCRIPTION
        "Cisco UCS fabric:FcMonDestEp:type managed object property"
    ::= { cucsFabricFcMonDestEpEntry 20 }

cucsFabricFcMonDestEpPeerChassisId OBJECT-TYPE
    SYNTAX       Gauge32
    MAX-ACCESS   read-only
    STATUS       current
    DESCRIPTION
        "Cisco UCS fabric:FcMonDestEp:peerChassisId managed
        object property"
    ::= { cucsFabricFcMonDestEpEntry 21 }

cucsFabricFcMonDestEpFltAggr OBJECT-TYPE
    SYNTAX       Unsigned64
    MAX-ACCESS   read-only
    STATUS       current
    DESCRIPTION
        "Cisco UCS fabric:FcMonDestEp:fltAggr managed object property"
    ::= { cucsFabricFcMonDestEpEntry 22 }

cucsFabricFcMonFiltEpTable OBJECT-TYPE
    SYNTAX           SEQUENCE OF CucsFabricFcMonFiltEpEntry
    MAX-ACCESS       not-accessible
    STATUS           current
    DESCRIPTION
        "Cisco UCS fabric:FcMonFiltEp managed object table"
    ::= { cucsFabricObjects 30 }

cucsFabricFcMonFiltEpEntry OBJECT-TYPE
    SYNTAX           CucsFabricFcMonFiltEpEntry
    MAX-ACCESS       not-accessible
    STATUS           current
    DESCRIPTION
        "Entry for the cucsFabricFcMonFiltEpTable table."
    INDEX { cucsFabricFcMonFiltEpInstanceId }
    ::= { cucsFabricFcMonFiltEpTable 1 }

CucsFabricFcMonFiltEpEntry ::= SEQUENCE {
    cucsFabricFcMonFiltEpInstanceId                                  CucsManagedObjectId,
    cucsFabricFcMonFiltEpDn                                          CucsManagedObjectDn,
    cucsFabricFcMonFiltEpRn                                          SnmpAdminString,
    cucsFabricFcMonFiltEpName                                        SnmpAdminString,
    cucsFabricFcMonFiltEpSession                                     Gauge32,
    cucsFabricFcMonFiltEpType                                        CucsFabricFcMonFiltEpType
}

cucsFabricFcMonFiltEpInstanceId OBJECT-TYPE
    SYNTAX       CucsManagedObjectId
    MAX-ACCESS   not-accessible
    STATUS       current
    DESCRIPTION
        "Instance identifier of the managed object."
    ::= { cucsFabricFcMonFiltEpEntry 1 }

cucsFabricFcMonFiltEpDn OBJECT-TYPE
    SYNTAX       CucsManagedObjectDn
    MAX-ACCESS   read-only
    STATUS       current
    DESCRIPTION
        "Cisco UCS fabric:FcMonFiltEp:dn managed object property"
    ::= { cucsFabricFcMonFiltEpEntry 2 }

cucsFabricFcMonFiltEpRn OBJECT-TYPE
    SYNTAX       SnmpAdminString
    MAX-ACCESS   read-only
    STATUS       current
    DESCRIPTION
        "Cisco UCS fabric:FcMonFiltEp:rn managed object property"
    ::= { cucsFabricFcMonFiltEpEntry 3 }

cucsFabricFcMonFiltEpName OBJECT-TYPE
    SYNTAX       SnmpAdminString
    MAX-ACCESS   read-only
    STATUS       current
    DESCRIPTION
        "Cisco UCS fabric:FcMonFiltEp:name managed object property"
    ::= { cucsFabricFcMonFiltEpEntry 4 }

cucsFabricFcMonFiltEpSession OBJECT-TYPE
    SYNTAX       Gauge32
    MAX-ACCESS   read-only
    STATUS       current
    DESCRIPTION
        "Cisco UCS fabric:FcMonFiltEp:session managed object property"
    ::= { cucsFabricFcMonFiltEpEntry 5 }

cucsFabricFcMonFiltEpType OBJECT-TYPE
    SYNTAX       CucsFabricFcMonFiltEpType
    MAX-ACCESS   read-only
    STATUS       current
    DESCRIPTION
        "Cisco UCS fabric:FcMonFiltEp:type managed object property"
    ::= { cucsFabricFcMonFiltEpEntry 6 }

cucsFabricFcMonFiltRefTable OBJECT-TYPE
    SYNTAX           SEQUENCE OF CucsFabricFcMonFiltRefEntry
    MAX-ACCESS       not-accessible
    STATUS           current
    DESCRIPTION
        "Cisco UCS fabric:FcMonFiltRef managed object table"
    ::= { cucsFabricObjects 31 }

cucsFabricFcMonFiltRefEntry OBJECT-TYPE
    SYNTAX           CucsFabricFcMonFiltRefEntry
    MAX-ACCESS       not-accessible
    STATUS           current
    DESCRIPTION
        "Entry for the cucsFabricFcMonFiltRefTable table."
    INDEX { cucsFabricFcMonFiltRefInstanceId }
    ::= { cucsFabricFcMonFiltRefTable 1 }

CucsFabricFcMonFiltRefEntry ::= SEQUENCE {
    cucsFabricFcMonFiltRefInstanceId                                 CucsManagedObjectId,
    cucsFabricFcMonFiltRefDn                                         CucsManagedObjectDn,
    cucsFabricFcMonFiltRefRn                                         SnmpAdminString,
    cucsFabricFcMonFiltRefSrcFiltDn                                  SnmpAdminString,
    cucsFabricFcMonFiltRefType                                       CucsFabricFcMonFiltRefType
}

cucsFabricFcMonFiltRefInstanceId OBJECT-TYPE
    SYNTAX       CucsManagedObjectId
    MAX-ACCESS   not-accessible
    STATUS       current
    DESCRIPTION
        "Instance identifier of the managed object."
    ::= { cucsFabricFcMonFiltRefEntry 1 }

cucsFabricFcMonFiltRefDn OBJECT-TYPE
    SYNTAX       CucsManagedObjectDn
    MAX-ACCESS   read-only
    STATUS       current
    DESCRIPTION
        "Cisco UCS fabric:FcMonFiltRef:dn managed object property"
    ::= { cucsFabricFcMonFiltRefEntry 2 }

cucsFabricFcMonFiltRefRn OBJECT-TYPE
    SYNTAX       SnmpAdminString
    MAX-ACCESS   read-only
    STATUS       current
    DESCRIPTION
        "Cisco UCS fabric:FcMonFiltRef:rn managed object property"
    ::= { cucsFabricFcMonFiltRefEntry 3 }

cucsFabricFcMonFiltRefSrcFiltDn OBJECT-TYPE
    SYNTAX       SnmpAdminString
    MAX-ACCESS   read-only
    STATUS       current
    DESCRIPTION
        "Cisco UCS fabric:FcMonFiltRef:srcFiltDn managed object property"
    ::= { cucsFabricFcMonFiltRefEntry 4 }

cucsFabricFcMonFiltRefType OBJECT-TYPE
    SYNTAX       CucsFabricFcMonFiltRefType
    MAX-ACCESS   read-only
    STATUS       current
    DESCRIPTION
        "Cisco UCS fabric:FcMonFiltRef:type managed object property"
    ::= { cucsFabricFcMonFiltRefEntry 5 }

cucsFabricFcMonSanTable OBJECT-TYPE
    SYNTAX           SEQUENCE OF CucsFabricFcMonSanEntry
    MAX-ACCESS       not-accessible
    STATUS           current
    DESCRIPTION
        "Cisco UCS fabric:FcMonSan managed object table"
    ::= { cucsFabricObjects 32 }

cucsFabricFcMonSanEntry OBJECT-TYPE
    SYNTAX           CucsFabricFcMonSanEntry
    MAX-ACCESS       not-accessible
    STATUS           current
    DESCRIPTION
        "Entry for the cucsFabricFcMonSanTable table."
    INDEX { cucsFabricFcMonSanInstanceId }
    ::= { cucsFabricFcMonSanTable 1 }

CucsFabricFcMonSanEntry ::= SEQUENCE {
    cucsFabricFcMonSanInstanceId                                     CucsManagedObjectId,
    cucsFabricFcMonSanDn                                             CucsManagedObjectDn,
    cucsFabricFcMonSanRn                                             SnmpAdminString,
    cucsFabricFcMonSanId                                             CucsNetworkSwitchId,
    cucsFabricFcMonSanLocale                                         CucsFabricExternalLocale,
    cucsFabricFcMonSanName                                           SnmpAdminString,
    cucsFabricFcMonSanTransport                                      CucsFabricFcMonSanTransport,
    cucsFabricFcMonSanType                                           CucsFabricFcMonSanType
}

cucsFabricFcMonSanInstanceId OBJECT-TYPE
    SYNTAX       CucsManagedObjectId
    MAX-ACCESS   not-accessible
    STATUS       current
    DESCRIPTION
        "Instance identifier of the managed object."
    ::= { cucsFabricFcMonSanEntry 1 }

cucsFabricFcMonSanDn OBJECT-TYPE
    SYNTAX       CucsManagedObjectDn
    MAX-ACCESS   read-only
    STATUS       current
    DESCRIPTION
        "Cisco UCS fabric:FcMonSan:dn managed object property"
    ::= { cucsFabricFcMonSanEntry 2 }

cucsFabricFcMonSanRn OBJECT-TYPE
    SYNTAX       SnmpAdminString
    MAX-ACCESS   read-only
    STATUS       current
    DESCRIPTION
        "Cisco UCS fabric:FcMonSan:rn managed object property"
    ::= { cucsFabricFcMonSanEntry 3 }

cucsFabricFcMonSanId OBJECT-TYPE
    SYNTAX       CucsNetworkSwitchId
    MAX-ACCESS   read-only
    STATUS       current
    DESCRIPTION
        "Cisco UCS fabric:FcMonSan:id managed object property"
    ::= { cucsFabricFcMonSanEntry 4 }

cucsFabricFcMonSanLocale OBJECT-TYPE
    SYNTAX       CucsFabricExternalLocale
    MAX-ACCESS   read-only
    STATUS       current
    DESCRIPTION
        "Cisco UCS fabric:FcMonSan:locale managed object property"
    ::= { cucsFabricFcMonSanEntry 5 }

cucsFabricFcMonSanName OBJECT-TYPE
    SYNTAX       SnmpAdminString
    MAX-ACCESS   read-only
    STATUS       current
    DESCRIPTION
        "Cisco UCS fabric:FcMonSan:name managed object property"
    ::= { cucsFabricFcMonSanEntry 6 }

cucsFabricFcMonSanTransport OBJECT-TYPE
    SYNTAX       CucsFabricFcMonSanTransport
    MAX-ACCESS   read-only
    STATUS       current
    DESCRIPTION
        "Cisco UCS fabric:FcMonSan:transport managed object property"
    ::= { cucsFabricFcMonSanEntry 7 }

cucsFabricFcMonSanType OBJECT-TYPE
    SYNTAX       CucsFabricFcMonSanType
    MAX-ACCESS   read-only
    STATUS       current
    DESCRIPTION
        "Cisco UCS fabric:FcMonSan:type managed object property"
    ::= { cucsFabricFcMonSanEntry 8 }

cucsFabricFcMonSrcEpTable OBJECT-TYPE
    SYNTAX           SEQUENCE OF CucsFabricFcMonSrcEpEntry
    MAX-ACCESS       not-accessible
    STATUS           current
    DESCRIPTION
        "Cisco UCS fabric:FcMonSrcEp managed object table"
    ::= { cucsFabricObjects 33 }

cucsFabricFcMonSrcEpEntry OBJECT-TYPE
    SYNTAX           CucsFabricFcMonSrcEpEntry
    MAX-ACCESS       not-accessible
    STATUS           current
    DESCRIPTION
        "Entry for the cucsFabricFcMonSrcEpTable table."
    INDEX { cucsFabricFcMonSrcEpInstanceId }
    ::= { cucsFabricFcMonSrcEpTable 1 }

CucsFabricFcMonSrcEpEntry ::= SEQUENCE {
    cucsFabricFcMonSrcEpInstanceId                                   CucsManagedObjectId,
    cucsFabricFcMonSrcEpDn                                           CucsManagedObjectDn,
    cucsFabricFcMonSrcEpRn                                           SnmpAdminString,
    cucsFabricFcMonSrcEpDirection                                    CucsFabricTrafficDirection,
    cucsFabricFcMonSrcEpName                                         SnmpAdminString,
    cucsFabricFcMonSrcEpSession                                      Gauge32,
    cucsFabricFcMonSrcEpTransport                                    CucsNetworkTransport,
    cucsFabricFcMonSrcEpType                                         CucsFabricFcMonSrcEpType
}

cucsFabricFcMonSrcEpInstanceId OBJECT-TYPE
    SYNTAX       CucsManagedObjectId
    MAX-ACCESS   not-accessible
    STATUS       current
    DESCRIPTION
        "Instance identifier of the managed object."
    ::= { cucsFabricFcMonSrcEpEntry 1 }

cucsFabricFcMonSrcEpDn OBJECT-TYPE
    SYNTAX       CucsManagedObjectDn
    MAX-ACCESS   read-only
    STATUS       current
    DESCRIPTION
        "Cisco UCS fabric:FcMonSrcEp:dn managed object property"
    ::= { cucsFabricFcMonSrcEpEntry 2 }

cucsFabricFcMonSrcEpRn OBJECT-TYPE
    SYNTAX       SnmpAdminString
    MAX-ACCESS   read-only
    STATUS       current
    DESCRIPTION
        "Cisco UCS fabric:FcMonSrcEp:rn managed object property"
    ::= { cucsFabricFcMonSrcEpEntry 3 }

cucsFabricFcMonSrcEpDirection OBJECT-TYPE
    SYNTAX       CucsFabricTrafficDirection
    MAX-ACCESS   read-only
    STATUS       current
    DESCRIPTION
        "Cisco UCS fabric:FcMonSrcEp:direction managed object property"
    ::= { cucsFabricFcMonSrcEpEntry 4 }

cucsFabricFcMonSrcEpName OBJECT-TYPE
    SYNTAX       SnmpAdminString
    MAX-ACCESS   read-only
    STATUS       current
    DESCRIPTION
        "Cisco UCS fabric:FcMonSrcEp:name managed object property"
    ::= { cucsFabricFcMonSrcEpEntry 5 }

cucsFabricFcMonSrcEpSession OBJECT-TYPE
    SYNTAX       Gauge32
    MAX-ACCESS   read-only
    STATUS       current
    DESCRIPTION
        "Cisco UCS fabric:FcMonSrcEp:session managed object property"
    ::= { cucsFabricFcMonSrcEpEntry 6 }

cucsFabricFcMonSrcEpTransport OBJECT-TYPE
    SYNTAX       CucsNetworkTransport
    MAX-ACCESS   read-only
    STATUS       current
    DESCRIPTION
        "Cisco UCS fabric:FcMonSrcEp:transport managed object property"
    ::= { cucsFabricFcMonSrcEpEntry 7 }

cucsFabricFcMonSrcEpType OBJECT-TYPE
    SYNTAX       CucsFabricFcMonSrcEpType
    MAX-ACCESS   read-only
    STATUS       current
    DESCRIPTION
        "Cisco UCS fabric:FcMonSrcEp:type managed object property"
    ::= { cucsFabricFcMonSrcEpEntry 8 }

cucsFabricFcMonSrcRefTable OBJECT-TYPE
    SYNTAX           SEQUENCE OF CucsFabricFcMonSrcRefEntry
    MAX-ACCESS       not-accessible
    STATUS           current
    DESCRIPTION
        "Cisco UCS fabric:FcMonSrcRef managed object table"
    ::= { cucsFabricObjects 34 }

cucsFabricFcMonSrcRefEntry OBJECT-TYPE
    SYNTAX           CucsFabricFcMonSrcRefEntry
    MAX-ACCESS       not-accessible
    STATUS           current
    DESCRIPTION
        "Entry for the cucsFabricFcMonSrcRefTable table."
    INDEX { cucsFabricFcMonSrcRefInstanceId }
    ::= { cucsFabricFcMonSrcRefTable 1 }

CucsFabricFcMonSrcRefEntry ::= SEQUENCE {
    cucsFabricFcMonSrcRefInstanceId                                  CucsManagedObjectId,
    cucsFabricFcMonSrcRefDn                                          CucsManagedObjectDn,
    cucsFabricFcMonSrcRefRn                                          SnmpAdminString,
    cucsFabricFcMonSrcRefId                                          Unsigned64,
    cucsFabricFcMonSrcRefSourceDn                                    SnmpAdminString,
    cucsFabricFcMonSrcRefSourceType                                  CucsFabricFcSourceType,
    cucsFabricFcMonSrcRefType                                        CucsFabricFcMonSrcRefType
}

cucsFabricFcMonSrcRefInstanceId OBJECT-TYPE
    SYNTAX       CucsManagedObjectId
    MAX-ACCESS   not-accessible
    STATUS       current
    DESCRIPTION
        "Instance identifier of the managed object."
    ::= { cucsFabricFcMonSrcRefEntry 1 }

cucsFabricFcMonSrcRefDn OBJECT-TYPE
    SYNTAX       CucsManagedObjectDn
    MAX-ACCESS   read-only
    STATUS       current
    DESCRIPTION
        "Cisco UCS fabric:FcMonSrcRef:dn managed object property"
    ::= { cucsFabricFcMonSrcRefEntry 2 }

cucsFabricFcMonSrcRefRn OBJECT-TYPE
    SYNTAX       SnmpAdminString
    MAX-ACCESS   read-only
    STATUS       current
    DESCRIPTION
        "Cisco UCS fabric:FcMonSrcRef:rn managed object property"
    ::= { cucsFabricFcMonSrcRefEntry 3 }

cucsFabricFcMonSrcRefId OBJECT-TYPE
    SYNTAX       Unsigned64
    MAX-ACCESS   read-only
    STATUS       current
    DESCRIPTION
        "Cisco UCS fabric:FcMonSrcRef:id managed object property"
    ::= { cucsFabricFcMonSrcRefEntry 4 }

cucsFabricFcMonSrcRefSourceDn OBJECT-TYPE
    SYNTAX       SnmpAdminString
    MAX-ACCESS   read-only
    STATUS       current
    DESCRIPTION
        "Cisco UCS fabric:FcMonSrcRef:sourceDn managed object property"
    ::= { cucsFabricFcMonSrcRefEntry 5 }

cucsFabricFcMonSrcRefSourceType OBJECT-TYPE
    SYNTAX       CucsFabricFcSourceType
    MAX-ACCESS   read-only
    STATUS       current
    DESCRIPTION
        "Cisco UCS fabric:FcMonSrcRef:sourceType managed object property"
    ::= { cucsFabricFcMonSrcRefEntry 6 }

cucsFabricFcMonSrcRefType OBJECT-TYPE
    SYNTAX       CucsFabricFcMonSrcRefType
    MAX-ACCESS   read-only
    STATUS       current
    DESCRIPTION
        "Cisco UCS fabric:FcMonSrcRef:type managed object property"
    ::= { cucsFabricFcMonSrcRefEntry 7 }

cucsFabricFcSanTable OBJECT-TYPE
    SYNTAX           SEQUENCE OF CucsFabricFcSanEntry
    MAX-ACCESS       not-accessible
    STATUS           current
    DESCRIPTION
        "Cisco UCS fabric:FcSan managed object table"
    ::= { cucsFabricObjects 35 }

cucsFabricFcSanEntry OBJECT-TYPE
    SYNTAX           CucsFabricFcSanEntry
    MAX-ACCESS       not-accessible
    STATUS           current
    DESCRIPTION
        "Entry for the cucsFabricFcSanTable table."
    INDEX { cucsFabricFcSanInstanceId }
    ::= { cucsFabricFcSanTable 1 }

CucsFabricFcSanEntry ::= SEQUENCE {
    cucsFabricFcSanInstanceId                                        CucsManagedObjectId,
    cucsFabricFcSanDn                                                CucsManagedObjectDn,
    cucsFabricFcSanRn                                                SnmpAdminString,
    cucsFabricFcSanId                                                CucsNetworkSwitchId,
    cucsFabricFcSanLocale                                            CucsFabricExternalLocale,
    cucsFabricFcSanName                                              SnmpAdminString,
    cucsFabricFcSanTransport                                         CucsFabricFcSanTransport,
    cucsFabricFcSanType                                              CucsFabricSanType,
    cucsFabricFcSanUplinkTrunking                                    CucsFabricFcSanUplinkTrunking
}

cucsFabricFcSanInstanceId OBJECT-TYPE
    SYNTAX       CucsManagedObjectId
    MAX-ACCESS   not-accessible
    STATUS       current
    DESCRIPTION
        "Instance identifier of the managed object."
    ::= { cucsFabricFcSanEntry 1 }

cucsFabricFcSanDn OBJECT-TYPE
    SYNTAX       CucsManagedObjectDn
    MAX-ACCESS   read-only
    STATUS       current
    DESCRIPTION
        "Cisco UCS fabric:FcSan:dn managed object property"
    ::= { cucsFabricFcSanEntry 2 }

cucsFabricFcSanRn OBJECT-TYPE
    SYNTAX       SnmpAdminString
    MAX-ACCESS   read-only
    STATUS       current
    DESCRIPTION
        "Cisco UCS fabric:FcSan:rn managed object property"
    ::= { cucsFabricFcSanEntry 3 }

cucsFabricFcSanId OBJECT-TYPE
    SYNTAX       CucsNetworkSwitchId
    MAX-ACCESS   read-only
    STATUS       current
    DESCRIPTION
        "Cisco UCS fabric:FcSan:id managed object property"
    ::= { cucsFabricFcSanEntry 4 }

cucsFabricFcSanLocale OBJECT-TYPE
    SYNTAX       CucsFabricExternalLocale
    MAX-ACCESS   read-only
    STATUS       current
    DESCRIPTION
        "Cisco UCS fabric:FcSan:locale managed object property"
    ::= { cucsFabricFcSanEntry 5 }

cucsFabricFcSanName OBJECT-TYPE
    SYNTAX       SnmpAdminString
    MAX-ACCESS   read-only
    STATUS       current
    DESCRIPTION
        "Cisco UCS fabric:FcSan:name managed object property"
    ::= { cucsFabricFcSanEntry 6 }

cucsFabricFcSanTransport OBJECT-TYPE
    SYNTAX       CucsFabricFcSanTransport
    MAX-ACCESS   read-only
    STATUS       current
    DESCRIPTION
        "Cisco UCS fabric:FcSan:transport managed object property"
    ::= { cucsFabricFcSanEntry 7 }

cucsFabricFcSanType OBJECT-TYPE
    SYNTAX       CucsFabricSanType
    MAX-ACCESS   read-only
    STATUS       current
    DESCRIPTION
        "Cisco UCS fabric:FcSan:type managed object property"
    ::= { cucsFabricFcSanEntry 8 }

cucsFabricFcSanUplinkTrunking OBJECT-TYPE
    SYNTAX       CucsFabricFcSanUplinkTrunking
    MAX-ACCESS   read-only
    STATUS       current
    DESCRIPTION
        "Cisco UCS fabric:FcSan:uplinkTrunking managed object property"
    ::= { cucsFabricFcSanEntry 9 }

cucsFabricFcSanEpTable OBJECT-TYPE
    SYNTAX           SEQUENCE OF CucsFabricFcSanEpEntry
    MAX-ACCESS       not-accessible
    STATUS           current
    DESCRIPTION
        "Cisco UCS fabric:FcSanEp managed object table"
    ::= { cucsFabricObjects 36 }

cucsFabricFcSanEpEntry OBJECT-TYPE
    SYNTAX           CucsFabricFcSanEpEntry
    MAX-ACCESS       not-accessible
    STATUS           current
    DESCRIPTION
        "Entry for the cucsFabricFcSanEpTable table."
    INDEX { cucsFabricFcSanEpInstanceId }
    ::= { cucsFabricFcSanEpTable 1 }

CucsFabricFcSanEpEntry ::= SEQUENCE {
    cucsFabricFcSanEpInstanceId                                      CucsManagedObjectId,
    cucsFabricFcSanEpDn                                              CucsManagedObjectDn,
    cucsFabricFcSanEpRn                                              SnmpAdminString,
    cucsFabricFcSanEpAdminState                                      CucsFabricExternalEpAdminState,
    cucsFabricFcSanEpChassisId                                       Gauge32,
    cucsFabricFcSanEpEpDn                                            SnmpAdminString,
    cucsFabricFcSanEpIfRole                                          CucsFabricSanEpIfRole,
    cucsFabricFcSanEpIfType                                          CucsFabricPIoEpIfType,
    cucsFabricFcSanEpLicGP                                           Unsigned64,
    cucsFabricFcSanEpLicState                                        CucsLicenseState,
    cucsFabricFcSanEpLocale                                          CucsFabricExternalEpLocale,
    cucsFabricFcSanEpName                                            SnmpAdminString,
    cucsFabricFcSanEpPeerDn                                          SnmpAdminString,
    cucsFabricFcSanEpPeerPortId                                      Gauge32,
    cucsFabricFcSanEpPeerSlotId                                      Gauge32,
    cucsFabricFcSanEpPortId                                          CucsFabricFcSanEpPortId,
    cucsFabricFcSanEpSlotId                                          CucsFabricFcSanEpSlotId,
    cucsFabricFcSanEpSwitchId                                        CucsNetworkSwitchId,
    cucsFabricFcSanEpTransport                                       CucsFabricAFcSanEpTransport,
    cucsFabricFcSanEpType                                            CucsFabricSanEpType,
    cucsFabricFcSanEpUsrLbl                                          SnmpAdminString,
    cucsFabricFcSanEpPeerChassisId                                   Gauge32,
    cucsFabricFcSanEpFltAggr                                         Unsigned64
}

cucsFabricFcSanEpInstanceId OBJECT-TYPE
    SYNTAX       CucsManagedObjectId
    MAX-ACCESS   not-accessible
    STATUS       current
    DESCRIPTION
        "Instance identifier of the managed object."
    ::= { cucsFabricFcSanEpEntry 1 }

cucsFabricFcSanEpDn OBJECT-TYPE
    SYNTAX       CucsManagedObjectDn
    MAX-ACCESS   read-only
    STATUS       current
    DESCRIPTION
        "Cisco UCS fabric:FcSanEp:dn managed object property"
    ::= { cucsFabricFcSanEpEntry 2 }

cucsFabricFcSanEpRn OBJECT-TYPE
    SYNTAX       SnmpAdminString
    MAX-ACCESS   read-only
    STATUS       current
    DESCRIPTION
        "Cisco UCS fabric:FcSanEp:rn managed object property"
    ::= { cucsFabricFcSanEpEntry 3 }

cucsFabricFcSanEpAdminState OBJECT-TYPE
    SYNTAX       CucsFabricExternalEpAdminState
    MAX-ACCESS   read-only
    STATUS       current
    DESCRIPTION
        "Cisco UCS fabric:FcSanEp:adminState managed object property"
    ::= { cucsFabricFcSanEpEntry 4 }

cucsFabricFcSanEpChassisId OBJECT-TYPE
    SYNTAX       Gauge32
    MAX-ACCESS   read-only
    STATUS       current
    DESCRIPTION
        "Cisco UCS fabric:FcSanEp:chassisId managed object property"
    ::= { cucsFabricFcSanEpEntry 5 }

cucsFabricFcSanEpEpDn OBJECT-TYPE
    SYNTAX       SnmpAdminString
    MAX-ACCESS   read-only
    STATUS       current
    DESCRIPTION
        "Cisco UCS fabric:FcSanEp:epDn managed object property"
    ::= { cucsFabricFcSanEpEntry 6 }

cucsFabricFcSanEpIfRole OBJECT-TYPE
    SYNTAX       CucsFabricSanEpIfRole
    MAX-ACCESS   read-only
    STATUS       current
    DESCRIPTION
        "Cisco UCS fabric:FcSanEp:ifRole managed object property"
    ::= { cucsFabricFcSanEpEntry 7 }

cucsFabricFcSanEpIfType OBJECT-TYPE
    SYNTAX       CucsFabricPIoEpIfType
    MAX-ACCESS   read-only
    STATUS       current
    DESCRIPTION
        "Cisco UCS fabric:FcSanEp:ifType managed object property"
    ::= { cucsFabricFcSanEpEntry 8 }

cucsFabricFcSanEpLicGP OBJECT-TYPE
    SYNTAX       Unsigned64
    MAX-ACCESS   read-only
    STATUS       current
    DESCRIPTION
        "Cisco UCS fabric:FcSanEp:licGP managed object property"
    ::= { cucsFabricFcSanEpEntry 9 }

cucsFabricFcSanEpLicState OBJECT-TYPE
    SYNTAX       CucsLicenseState
    MAX-ACCESS   read-only
    STATUS       current
    DESCRIPTION
        "Cisco UCS fabric:FcSanEp:licState managed object property"
    ::= { cucsFabricFcSanEpEntry 10 }

cucsFabricFcSanEpLocale OBJECT-TYPE
    SYNTAX       CucsFabricExternalEpLocale
    MAX-ACCESS   read-only
    STATUS       current
    DESCRIPTION
        "Cisco UCS fabric:FcSanEp:locale managed object property"
    ::= { cucsFabricFcSanEpEntry 11 }

cucsFabricFcSanEpName OBJECT-TYPE
    SYNTAX       SnmpAdminString
    MAX-ACCESS   read-only
    STATUS       current
    DESCRIPTION
        "Cisco UCS fabric:FcSanEp:name managed object property"
    ::= { cucsFabricFcSanEpEntry 12 }

cucsFabricFcSanEpPeerDn OBJECT-TYPE
    SYNTAX       SnmpAdminString
    MAX-ACCESS   read-only
    STATUS       current
    DESCRIPTION
        "Cisco UCS fabric:FcSanEp:peerDn managed object property"
    ::= { cucsFabricFcSanEpEntry 13 }

cucsFabricFcSanEpPeerPortId OBJECT-TYPE
    SYNTAX       Gauge32
    MAX-ACCESS   read-only
    STATUS       current
    DESCRIPTION
        "Cisco UCS fabric:FcSanEp:peerPortId managed object property"
    ::= { cucsFabricFcSanEpEntry 14 }

cucsFabricFcSanEpPeerSlotId OBJECT-TYPE
    SYNTAX       Gauge32
    MAX-ACCESS   read-only
    STATUS       current
    DESCRIPTION
        "Cisco UCS fabric:FcSanEp:peerSlotId managed object property"
    ::= { cucsFabricFcSanEpEntry 15 }

cucsFabricFcSanEpPortId OBJECT-TYPE
    SYNTAX       CucsFabricFcSanEpPortId
    MAX-ACCESS   read-only
    STATUS       current
    DESCRIPTION
        "Cisco UCS fabric:FcSanEp:portId managed object property"
    ::= { cucsFabricFcSanEpEntry 16 }

cucsFabricFcSanEpSlotId OBJECT-TYPE
    SYNTAX       CucsFabricFcSanEpSlotId
    MAX-ACCESS   read-only
    STATUS       current
    DESCRIPTION
        "Cisco UCS fabric:FcSanEp:slotId managed object property"
    ::= { cucsFabricFcSanEpEntry 17 }

cucsFabricFcSanEpSwitchId OBJECT-TYPE
    SYNTAX       CucsNetworkSwitchId
    MAX-ACCESS   read-only
    STATUS       current
    DESCRIPTION
        "Cisco UCS fabric:FcSanEp:switchId managed object property"
    ::= { cucsFabricFcSanEpEntry 18 }

cucsFabricFcSanEpTransport OBJECT-TYPE
    SYNTAX       CucsFabricAFcSanEpTransport
    MAX-ACCESS   read-only
    STATUS       current
    DESCRIPTION
        "Cisco UCS fabric:FcSanEp:transport managed object property"
    ::= { cucsFabricFcSanEpEntry 19 }

cucsFabricFcSanEpType OBJECT-TYPE
    SYNTAX       CucsFabricSanEpType
    MAX-ACCESS   read-only
    STATUS       current
    DESCRIPTION
        "Cisco UCS fabric:FcSanEp:type managed object property"
    ::= { cucsFabricFcSanEpEntry 20 }

cucsFabricFcSanEpUsrLbl OBJECT-TYPE
    SYNTAX       SnmpAdminString
    MAX-ACCESS   read-only
    STATUS       current
    DESCRIPTION
        "Cisco UCS fabric:FcSanEp:usrLbl managed object property"
    ::= { cucsFabricFcSanEpEntry 21 }

cucsFabricFcSanEpPeerChassisId OBJECT-TYPE
    SYNTAX       Gauge32
    MAX-ACCESS   read-only
    STATUS       current
    DESCRIPTION
        "Cisco UCS fabric:FcSanEp:peerChassisId managed object property"
    ::= { cucsFabricFcSanEpEntry 22 }

cucsFabricFcSanEpFltAggr OBJECT-TYPE
    SYNTAX       Unsigned64
    MAX-ACCESS   read-only
    STATUS       current
    DESCRIPTION
        "Cisco UCS fabric:FcSanEp:fltAggr managed object property"
    ::= { cucsFabricFcSanEpEntry 23 }

cucsFabricFcSanPcTable OBJECT-TYPE
    SYNTAX           SEQUENCE OF CucsFabricFcSanPcEntry
    MAX-ACCESS       not-accessible
    STATUS           current
    DESCRIPTION
        "Cisco UCS fabric:FcSanPc managed object table"
    ::= { cucsFabricObjects 37 }

cucsFabricFcSanPcEntry OBJECT-TYPE
    SYNTAX           CucsFabricFcSanPcEntry
    MAX-ACCESS       not-accessible
    STATUS           current
    DESCRIPTION
        "Entry for the cucsFabricFcSanPcTable table."
    INDEX { cucsFabricFcSanPcInstanceId }
    ::= { cucsFabricFcSanPcTable 1 }

CucsFabricFcSanPcEntry ::= SEQUENCE {
    cucsFabricFcSanPcInstanceId                                      CucsManagedObjectId,
    cucsFabricFcSanPcDn                                              CucsManagedObjectDn,
    cucsFabricFcSanPcRn                                              SnmpAdminString,
    cucsFabricFcSanPcAdminState                                      CucsFabricAdminState,
    cucsFabricFcSanPcEndPtDn                                         SnmpAdminString,
    cucsFabricFcSanPcFltAggr                                         Unsigned64,
    cucsFabricFcSanPcIfRole                                          CucsFabricSanPcIfRole,
    cucsFabricFcSanPcIfType                                          CucsFabricCIoEpIfType,
    cucsFabricFcSanPcLocale                                          CucsFabricExternalPcLocale,
    cucsFabricFcSanPcName                                            SnmpAdminString,
    cucsFabricFcSanPcOperState                                       CucsNetworkPortOperState,
    cucsFabricFcSanPcPeerDn                                          SnmpAdminString,
    cucsFabricFcSanPcPortId                                          Gauge32,
    cucsFabricFcSanPcStateQual                                       SnmpAdminString,
    cucsFabricFcSanPcSwitchId                                        CucsNetworkSwitchId,
    cucsFabricFcSanPcTransport                                       CucsFabricFcSanPcTransport,
    cucsFabricFcSanPcType                                            CucsFabricSanPcType,
    cucsFabricFcSanPcAdminSpeed                                      CucsPortSpeed,
    cucsFabricFcSanPcConfigStatus                                    CucsFabricPcConfigStatus,
    cucsFabricFcSanPcOperSpeed                                       Gauge32
}

cucsFabricFcSanPcInstanceId OBJECT-TYPE
    SYNTAX       CucsManagedObjectId
    MAX-ACCESS   not-accessible
    STATUS       current
    DESCRIPTION
        "Instance identifier of the managed object."
    ::= { cucsFabricFcSanPcEntry 1 }

cucsFabricFcSanPcDn OBJECT-TYPE
    SYNTAX       CucsManagedObjectDn
    MAX-ACCESS   read-only
    STATUS       current
    DESCRIPTION
        "Cisco UCS fabric:FcSanPc:dn managed object property"
    ::= { cucsFabricFcSanPcEntry 2 }

cucsFabricFcSanPcRn OBJECT-TYPE
    SYNTAX       SnmpAdminString
    MAX-ACCESS   read-only
    STATUS       current
    DESCRIPTION
        "Cisco UCS fabric:FcSanPc:rn managed object property"
    ::= { cucsFabricFcSanPcEntry 3 }

cucsFabricFcSanPcAdminState OBJECT-TYPE
    SYNTAX       CucsFabricAdminState
    MAX-ACCESS   read-only
    STATUS       current
    DESCRIPTION
        "Cisco UCS fabric:FcSanPc:adminState managed object property"
    ::= { cucsFabricFcSanPcEntry 4 }

cucsFabricFcSanPcEndPtDn OBJECT-TYPE
    SYNTAX       SnmpAdminString
    MAX-ACCESS   read-only
    STATUS       current
    DESCRIPTION
        "Cisco UCS fabric:FcSanPc:epDn managed object property"
    ::= { cucsFabricFcSanPcEntry 5 }

cucsFabricFcSanPcFltAggr OBJECT-TYPE
    SYNTAX       Unsigned64
    MAX-ACCESS   read-only
    STATUS       current
    DESCRIPTION
        "Cisco UCS fabric:FcSanPc:fltAggr managed object property"
    ::= { cucsFabricFcSanPcEntry 6 }

cucsFabricFcSanPcIfRole OBJECT-TYPE
    SYNTAX       CucsFabricSanPcIfRole
    MAX-ACCESS   read-only
    STATUS       current
    DESCRIPTION
        "Cisco UCS fabric:FcSanPc:ifRole managed object property"
    ::= { cucsFabricFcSanPcEntry 7 }

cucsFabricFcSanPcIfType OBJECT-TYPE
    SYNTAX       CucsFabricCIoEpIfType
    MAX-ACCESS   read-only
    STATUS       current
    DESCRIPTION
        "Cisco UCS fabric:FcSanPc:ifType managed object property"
    ::= { cucsFabricFcSanPcEntry 8 }

cucsFabricFcSanPcLocale OBJECT-TYPE
    SYNTAX       CucsFabricExternalPcLocale
    MAX-ACCESS   read-only
    STATUS       current
    DESCRIPTION
        "Cisco UCS fabric:FcSanPc:locale managed object property"
    ::= { cucsFabricFcSanPcEntry 9 }

cucsFabricFcSanPcName OBJECT-TYPE
    SYNTAX       SnmpAdminString
    MAX-ACCESS   read-only
    STATUS       current
    DESCRIPTION
        "Cisco UCS fabric:FcSanPc:name managed object property"
    ::= { cucsFabricFcSanPcEntry 10 }

cucsFabricFcSanPcOperState OBJECT-TYPE
    SYNTAX       CucsNetworkPortOperState
    MAX-ACCESS   read-only
    STATUS       current
    DESCRIPTION
        "Cisco UCS fabric:FcSanPc:operState managed object property"
    ::= { cucsFabricFcSanPcEntry 11 }

cucsFabricFcSanPcPeerDn OBJECT-TYPE
    SYNTAX       SnmpAdminString
    MAX-ACCESS   read-only
    STATUS       current
    DESCRIPTION
        "Cisco UCS fabric:FcSanPc:peerDn managed object property"
    ::= { cucsFabricFcSanPcEntry 12 }

cucsFabricFcSanPcPortId OBJECT-TYPE
    SYNTAX       Gauge32
    MAX-ACCESS   read-only
    STATUS       current
    DESCRIPTION
        "Cisco UCS fabric:FcSanPc:portId managed object property"
    ::= { cucsFabricFcSanPcEntry 13 }

cucsFabricFcSanPcStateQual OBJECT-TYPE
    SYNTAX       SnmpAdminString
    MAX-ACCESS   read-only
    STATUS       current
    DESCRIPTION
        "Cisco UCS fabric:FcSanPc:stateQual managed object property"
    ::= { cucsFabricFcSanPcEntry 14 }

cucsFabricFcSanPcSwitchId OBJECT-TYPE
    SYNTAX       CucsNetworkSwitchId
    MAX-ACCESS   read-only
    STATUS       current
    DESCRIPTION
        "Cisco UCS fabric:FcSanPc:switchId managed object property"
    ::= { cucsFabricFcSanPcEntry 15 }

cucsFabricFcSanPcTransport OBJECT-TYPE
    SYNTAX       CucsFabricFcSanPcTransport
    MAX-ACCESS   read-only
    STATUS       current
    DESCRIPTION
        "Cisco UCS fabric:FcSanPc:transport managed object property"
    ::= { cucsFabricFcSanPcEntry 16 }

cucsFabricFcSanPcType OBJECT-TYPE
    SYNTAX       CucsFabricSanPcType
    MAX-ACCESS   read-only
    STATUS       current
    DESCRIPTION
        "Cisco UCS fabric:FcSanPc:type managed object property"
    ::= { cucsFabricFcSanPcEntry 17 }

cucsFabricFcSanPcAdminSpeed OBJECT-TYPE
    SYNTAX       CucsPortSpeed
    MAX-ACCESS   read-only
    STATUS       current
    DESCRIPTION
        "Cisco UCS fabric:FcSanPc:adminSpeed managed object property"
    ::= { cucsFabricFcSanPcEntry 18 }

cucsFabricFcSanPcConfigStatus OBJECT-TYPE
    SYNTAX       CucsFabricPcConfigStatus
    MAX-ACCESS   read-only
    STATUS       current
    DESCRIPTION
        "Cisco UCS fabric:FcSanPc:configStatus managed object property"
    ::= { cucsFabricFcSanPcEntry 19 }

cucsFabricFcSanPcOperSpeed OBJECT-TYPE
    SYNTAX       Gauge32
    MAX-ACCESS   read-only
    STATUS       current
    DESCRIPTION
        "Cisco UCS fabric:FcSanPc:operSpeed managed object property"
    ::= { cucsFabricFcSanPcEntry 20 }

cucsFabricFcSanPcEpTable OBJECT-TYPE
    SYNTAX           SEQUENCE OF CucsFabricFcSanPcEpEntry
    MAX-ACCESS       not-accessible
    STATUS           current
    DESCRIPTION
        "Cisco UCS fabric:FcSanPcEp managed object table"
    ::= { cucsFabricObjects 38 }

cucsFabricFcSanPcEpEntry OBJECT-TYPE
    SYNTAX           CucsFabricFcSanPcEpEntry
    MAX-ACCESS       not-accessible
    STATUS           current
    DESCRIPTION
        "Entry for the cucsFabricFcSanPcEpTable table."
    INDEX { cucsFabricFcSanPcEpInstanceId }
    ::= { cucsFabricFcSanPcEpTable 1 }

CucsFabricFcSanPcEpEntry ::= SEQUENCE {
    cucsFabricFcSanPcEpInstanceId                                    CucsManagedObjectId,
    cucsFabricFcSanPcEpDn                                            CucsManagedObjectDn,
    cucsFabricFcSanPcEpRn                                            SnmpAdminString,
    cucsFabricFcSanPcEpAdminState                                    CucsFabricExternalEpAdminState,
    cucsFabricFcSanPcEpChassisId                                     Gauge32,
    cucsFabricFcSanPcEpEpDn                                          SnmpAdminString,
    cucsFabricFcSanPcEpIfRole                                        CucsFabricSanEpIfRole,
    cucsFabricFcSanPcEpIfType                                        CucsFabricPIoEpIfType,
    cucsFabricFcSanPcEpLicGP                                         Unsigned64,
    cucsFabricFcSanPcEpLicState                                      CucsLicenseState,
    cucsFabricFcSanPcEpLocale                                        CucsFabricExternalEpLocale,
    cucsFabricFcSanPcEpMembership                                    CucsFabricMembershipStatus,
    cucsFabricFcSanPcEpName                                          SnmpAdminString,
    cucsFabricFcSanPcEpPeerDn                                        SnmpAdminString,
    cucsFabricFcSanPcEpPeerPortId                                    Gauge32,
    cucsFabricFcSanPcEpPeerSlotId                                    Gauge32,
    cucsFabricFcSanPcEpPortId                                        CucsFabricFcSanPcEpPortId,
    cucsFabricFcSanPcEpSlotId                                        CucsFabricFcSanPcEpSlotId,
    cucsFabricFcSanPcEpSwitchId                                      CucsNetworkSwitchId,
    cucsFabricFcSanPcEpTransport                                     CucsFabricAFcSanEpTransport,
    cucsFabricFcSanPcEpType                                          CucsFabricSanEpType,
    cucsFabricFcSanPcEpAdminSpeed                                    CucsPortSpeed,
    cucsFabricFcSanPcEpPeerChassisId                                 Gauge32,
    cucsFabricFcSanPcEpFltAggr                                       Unsigned64
}

cucsFabricFcSanPcEpInstanceId OBJECT-TYPE
    SYNTAX       CucsManagedObjectId
    MAX-ACCESS   not-accessible
    STATUS       current
    DESCRIPTION
        "Instance identifier of the managed object."
    ::= { cucsFabricFcSanPcEpEntry 1 }

cucsFabricFcSanPcEpDn OBJECT-TYPE
    SYNTAX       CucsManagedObjectDn
    MAX-ACCESS   read-only
    STATUS       current
    DESCRIPTION
        "Cisco UCS fabric:FcSanPcEp:dn managed object property"
    ::= { cucsFabricFcSanPcEpEntry 2 }

cucsFabricFcSanPcEpRn OBJECT-TYPE
    SYNTAX       SnmpAdminString
    MAX-ACCESS   read-only
    STATUS       current
    DESCRIPTION
        "Cisco UCS fabric:FcSanPcEp:rn managed object property"
    ::= { cucsFabricFcSanPcEpEntry 3 }

cucsFabricFcSanPcEpAdminState OBJECT-TYPE
    SYNTAX       CucsFabricExternalEpAdminState
    MAX-ACCESS   read-only
    STATUS       current
    DESCRIPTION
        "Cisco UCS fabric:FcSanPcEp:adminState managed object property"
    ::= { cucsFabricFcSanPcEpEntry 4 }

cucsFabricFcSanPcEpChassisId OBJECT-TYPE
    SYNTAX       Gauge32
    MAX-ACCESS   read-only
    STATUS       current
    DESCRIPTION
        "Cisco UCS fabric:FcSanPcEp:chassisId managed object property"
    ::= { cucsFabricFcSanPcEpEntry 5 }

cucsFabricFcSanPcEpEpDn OBJECT-TYPE
    SYNTAX       SnmpAdminString
    MAX-ACCESS   read-only
    STATUS       current
    DESCRIPTION
        "Cisco UCS fabric:FcSanPcEp:epDn managed object property"
    ::= { cucsFabricFcSanPcEpEntry 6 }

cucsFabricFcSanPcEpIfRole OBJECT-TYPE
    SYNTAX       CucsFabricSanEpIfRole
    MAX-ACCESS   read-only
    STATUS       current
    DESCRIPTION
        "Cisco UCS fabric:FcSanPcEp:ifRole managed object property"
    ::= { cucsFabricFcSanPcEpEntry 7 }

cucsFabricFcSanPcEpIfType OBJECT-TYPE
    SYNTAX       CucsFabricPIoEpIfType
    MAX-ACCESS   read-only
    STATUS       current
    DESCRIPTION
        "Cisco UCS fabric:FcSanPcEp:ifType managed object property"
    ::= { cucsFabricFcSanPcEpEntry 8 }

cucsFabricFcSanPcEpLicGP OBJECT-TYPE
    SYNTAX       Unsigned64
    MAX-ACCESS   read-only
    STATUS       current
    DESCRIPTION
        "Cisco UCS fabric:FcSanPcEp:licGP managed object property"
    ::= { cucsFabricFcSanPcEpEntry 9 }

cucsFabricFcSanPcEpLicState OBJECT-TYPE
    SYNTAX       CucsLicenseState
    MAX-ACCESS   read-only
    STATUS       current
    DESCRIPTION
        "Cisco UCS fabric:FcSanPcEp:licState managed object property"
    ::= { cucsFabricFcSanPcEpEntry 10 }

cucsFabricFcSanPcEpLocale OBJECT-TYPE
    SYNTAX       CucsFabricExternalEpLocale
    MAX-ACCESS   read-only
    STATUS       current
    DESCRIPTION
        "Cisco UCS fabric:FcSanPcEp:locale managed object property"
    ::= { cucsFabricFcSanPcEpEntry 11 }

cucsFabricFcSanPcEpMembership OBJECT-TYPE
    SYNTAX       CucsFabricMembershipStatus
    MAX-ACCESS   read-only
    STATUS       current
    DESCRIPTION
        "Cisco UCS fabric:FcSanPcEp:membership managed object property"
    ::= { cucsFabricFcSanPcEpEntry 12 }

cucsFabricFcSanPcEpName OBJECT-TYPE
    SYNTAX       SnmpAdminString
    MAX-ACCESS   read-only
    STATUS       current
    DESCRIPTION
        "Cisco UCS fabric:FcSanPcEp:name managed object property"
    ::= { cucsFabricFcSanPcEpEntry 13 }

cucsFabricFcSanPcEpPeerDn OBJECT-TYPE
    SYNTAX       SnmpAdminString
    MAX-ACCESS   read-only
    STATUS       current
    DESCRIPTION
        "Cisco UCS fabric:FcSanPcEp:peerDn managed object property"
    ::= { cucsFabricFcSanPcEpEntry 14 }

cucsFabricFcSanPcEpPeerPortId OBJECT-TYPE
    SYNTAX       Gauge32
    MAX-ACCESS   read-only
    STATUS       current
    DESCRIPTION
        "Cisco UCS fabric:FcSanPcEp:peerPortId managed object property"
    ::= { cucsFabricFcSanPcEpEntry 15 }

cucsFabricFcSanPcEpPeerSlotId OBJECT-TYPE
    SYNTAX       Gauge32
    MAX-ACCESS   read-only
    STATUS       current
    DESCRIPTION
        "Cisco UCS fabric:FcSanPcEp:peerSlotId managed object property"
    ::= { cucsFabricFcSanPcEpEntry 16 }

cucsFabricFcSanPcEpPortId OBJECT-TYPE
    SYNTAX       CucsFabricFcSanPcEpPortId
    MAX-ACCESS   read-only
    STATUS       current
    DESCRIPTION
        "Cisco UCS fabric:FcSanPcEp:portId managed object property"
    ::= { cucsFabricFcSanPcEpEntry 17 }

cucsFabricFcSanPcEpSlotId OBJECT-TYPE
    SYNTAX       CucsFabricFcSanPcEpSlotId
    MAX-ACCESS   read-only
    STATUS       current
    DESCRIPTION
        "Cisco UCS fabric:FcSanPcEp:slotId managed object property"
    ::= { cucsFabricFcSanPcEpEntry 18 }

cucsFabricFcSanPcEpSwitchId OBJECT-TYPE
    SYNTAX       CucsNetworkSwitchId
    MAX-ACCESS   read-only
    STATUS       current
    DESCRIPTION
        "Cisco UCS fabric:FcSanPcEp:switchId managed object property"
    ::= { cucsFabricFcSanPcEpEntry 19 }

cucsFabricFcSanPcEpTransport OBJECT-TYPE
    SYNTAX       CucsFabricAFcSanEpTransport
    MAX-ACCESS   read-only
    STATUS       current
    DESCRIPTION
        "Cisco UCS fabric:FcSanPcEp:transport managed object property"
    ::= { cucsFabricFcSanPcEpEntry 20 }

cucsFabricFcSanPcEpType OBJECT-TYPE
    SYNTAX       CucsFabricSanEpType
    MAX-ACCESS   read-only
    STATUS       current
    DESCRIPTION
        "Cisco UCS fabric:FcSanPcEp:type managed object property"
    ::= { cucsFabricFcSanPcEpEntry 21 }

cucsFabricFcSanPcEpAdminSpeed OBJECT-TYPE
    SYNTAX       CucsPortSpeed
    MAX-ACCESS   read-only
    STATUS       current
    DESCRIPTION
        "Cisco UCS fabric:FcSanPcEp:adminSpeed managed object property"
    ::= { cucsFabricFcSanPcEpEntry 22 }

cucsFabricFcSanPcEpPeerChassisId OBJECT-TYPE
    SYNTAX       Gauge32
    MAX-ACCESS   read-only
    STATUS       current
    DESCRIPTION
        "Cisco UCS fabric:FcSanPcEp:peerChassisId managed object property"
    ::= { cucsFabricFcSanPcEpEntry 23 }

cucsFabricFcSanPcEpFltAggr OBJECT-TYPE
    SYNTAX       Unsigned64
    MAX-ACCESS   read-only
    STATUS       current
    DESCRIPTION
        "Cisco UCS fabric:FcSanPcEp:fltAggr managed object property"
    ::= { cucsFabricFcSanPcEpEntry 24 }

cucsFabricFcVsanPcTable OBJECT-TYPE
    SYNTAX           SEQUENCE OF CucsFabricFcVsanPcEntry
    MAX-ACCESS       not-accessible
    STATUS           current
    DESCRIPTION
        "Cisco UCS fabric:FcVsanPc managed object table"
    ::= { cucsFabricObjects 65 }

cucsFabricFcVsanPcEntry OBJECT-TYPE
    SYNTAX           CucsFabricFcVsanPcEntry
    MAX-ACCESS       not-accessible
    STATUS           current
    DESCRIPTION
        "Entry for the cucsFabricFcVsanPcTable table."
    INDEX { cucsFabricFcVsanPcInstanceId }
    ::= { cucsFabricFcVsanPcTable 1 }

CucsFabricFcVsanPcEntry ::= SEQUENCE {
    cucsFabricFcVsanPcInstanceId                                     CucsManagedObjectId,
    cucsFabricFcVsanPcDn                                             CucsManagedObjectDn,
    cucsFabricFcVsanPcRn                                             SnmpAdminString,
    cucsFabricFcVsanPcAdminState                                     CucsFabricAdminState,
    cucsFabricFcVsanPcEpDn                                           SnmpAdminString,
    cucsFabricFcVsanPcFltAggr                                        Unsigned64,
    cucsFabricFcVsanPcIfRole                                         CucsFabricSanPcIfRole,
    cucsFabricFcVsanPcIfType                                         CucsFabricCIoEpIfType,
    cucsFabricFcVsanPcLocale                                         CucsFabricExternalPcLocale,
    cucsFabricFcVsanPcName                                           SnmpAdminString,
    cucsFabricFcVsanPcOperState                                      CucsNetworkPortOperState,
    cucsFabricFcVsanPcPeerDn                                         SnmpAdminString,
    cucsFabricFcVsanPcPortId                                         Gauge32,
    cucsFabricFcVsanPcStateQual                                      SnmpAdminString,
    cucsFabricFcVsanPcSwitchId                                       CucsNetworkSwitchId,
    cucsFabricFcVsanPcTransport                                      CucsFabricFcVsanPcTransport,
    cucsFabricFcVsanPcType                                           CucsFabricSanPcType
}

cucsFabricFcVsanPcInstanceId OBJECT-TYPE
    SYNTAX       CucsManagedObjectId
    MAX-ACCESS   not-accessible
    STATUS       current
    DESCRIPTION
        "Instance identifier of the managed object."
    ::= { cucsFabricFcVsanPcEntry 1 }

cucsFabricFcVsanPcDn OBJECT-TYPE
    SYNTAX       CucsManagedObjectDn
    MAX-ACCESS   read-only
    STATUS       current
    DESCRIPTION
        "Cisco UCS fabric:FcVsanPc:dn managed object property"
    ::= { cucsFabricFcVsanPcEntry 2 }

cucsFabricFcVsanPcRn OBJECT-TYPE
    SYNTAX       SnmpAdminString
    MAX-ACCESS   read-only
    STATUS       current
    DESCRIPTION
        "Cisco UCS fabric:FcVsanPc:rn managed object property"
    ::= { cucsFabricFcVsanPcEntry 3 }

cucsFabricFcVsanPcAdminState OBJECT-TYPE
    SYNTAX       CucsFabricAdminState
    MAX-ACCESS   read-only
    STATUS       current
    DESCRIPTION
        "Cisco UCS fabric:FcVsanPc:adminState managed object property"
    ::= { cucsFabricFcVsanPcEntry 4 }

cucsFabricFcVsanPcEpDn OBJECT-TYPE
    SYNTAX       SnmpAdminString
    MAX-ACCESS   read-only
    STATUS       current
    DESCRIPTION
        "Cisco UCS fabric:FcVsanPc:epDn managed object property"
    ::= { cucsFabricFcVsanPcEntry 5 }

cucsFabricFcVsanPcFltAggr OBJECT-TYPE
    SYNTAX       Unsigned64
    MAX-ACCESS   read-only
    STATUS       current
    DESCRIPTION
        "Cisco UCS fabric:FcVsanPc:fltAggr managed object property"
    ::= { cucsFabricFcVsanPcEntry 6 }

cucsFabricFcVsanPcIfRole OBJECT-TYPE
    SYNTAX       CucsFabricSanPcIfRole
    MAX-ACCESS   read-only
    STATUS       current
    DESCRIPTION
        "Cisco UCS fabric:FcVsanPc:ifRole managed object property"
    ::= { cucsFabricFcVsanPcEntry 7 }

cucsFabricFcVsanPcIfType OBJECT-TYPE
    SYNTAX       CucsFabricCIoEpIfType
    MAX-ACCESS   read-only
    STATUS       current
    DESCRIPTION
        "Cisco UCS fabric:FcVsanPc:ifType managed object property"
    ::= { cucsFabricFcVsanPcEntry 8 }

cucsFabricFcVsanPcLocale OBJECT-TYPE
    SYNTAX       CucsFabricExternalPcLocale
    MAX-ACCESS   read-only
    STATUS       current
    DESCRIPTION
        "Cisco UCS fabric:FcVsanPc:locale managed object property"
    ::= { cucsFabricFcVsanPcEntry 9 }

cucsFabricFcVsanPcName OBJECT-TYPE
    SYNTAX       SnmpAdminString
    MAX-ACCESS   read-only
    STATUS       current
    DESCRIPTION
        "Cisco UCS fabric:FcVsanPc:name managed object property"
    ::= { cucsFabricFcVsanPcEntry 10 }

cucsFabricFcVsanPcOperState OBJECT-TYPE
    SYNTAX       CucsNetworkPortOperState
    MAX-ACCESS   read-only
    STATUS       current
    DESCRIPTION
        "Cisco UCS fabric:FcVsanPc:operState managed object property"
    ::= { cucsFabricFcVsanPcEntry 11 }

cucsFabricFcVsanPcPeerDn OBJECT-TYPE
    SYNTAX       SnmpAdminString
    MAX-ACCESS   read-only
    STATUS       current
    DESCRIPTION
        "Cisco UCS fabric:FcVsanPc:peerDn managed object property"
    ::= { cucsFabricFcVsanPcEntry 12 }

cucsFabricFcVsanPcPortId OBJECT-TYPE
    SYNTAX       Gauge32
    MAX-ACCESS   read-only
    STATUS       current
    DESCRIPTION
        "Cisco UCS fabric:FcVsanPc:portId managed object property"
    ::= { cucsFabricFcVsanPcEntry 13 }

cucsFabricFcVsanPcStateQual OBJECT-TYPE
    SYNTAX       SnmpAdminString
    MAX-ACCESS   read-only
    STATUS       current
    DESCRIPTION
        "Cisco UCS fabric:FcVsanPc:stateQual managed object property"
    ::= { cucsFabricFcVsanPcEntry 14 }

cucsFabricFcVsanPcSwitchId OBJECT-TYPE
    SYNTAX       CucsNetworkSwitchId
    MAX-ACCESS   read-only
    STATUS       current
    DESCRIPTION
        "Cisco UCS fabric:FcVsanPc:switchId managed object property"
    ::= { cucsFabricFcVsanPcEntry 15 }

cucsFabricFcVsanPcTransport OBJECT-TYPE
    SYNTAX       CucsFabricFcVsanPcTransport
    MAX-ACCESS   read-only
    STATUS       current
    DESCRIPTION
        "Cisco UCS fabric:FcVsanPc:transport managed object property"
    ::= { cucsFabricFcVsanPcEntry 16 }

cucsFabricFcVsanPcType OBJECT-TYPE
    SYNTAX       CucsFabricSanPcType
    MAX-ACCESS   read-only
    STATUS       current
    DESCRIPTION
        "Cisco UCS fabric:FcVsanPc:type managed object property"
    ::= { cucsFabricFcVsanPcEntry 17 }

cucsFabricFcVsanPortEpTable OBJECT-TYPE
    SYNTAX           SEQUENCE OF CucsFabricFcVsanPortEpEntry
    MAX-ACCESS       not-accessible
    STATUS           current
    DESCRIPTION
        "Cisco UCS fabric:FcVsanPortEp managed object table"
    ::= { cucsFabricObjects 39 }

cucsFabricFcVsanPortEpEntry OBJECT-TYPE
    SYNTAX           CucsFabricFcVsanPortEpEntry
    MAX-ACCESS       not-accessible
    STATUS           current
    DESCRIPTION
        "Entry for the cucsFabricFcVsanPortEpTable table."
    INDEX { cucsFabricFcVsanPortEpInstanceId }
    ::= { cucsFabricFcVsanPortEpTable 1 }

CucsFabricFcVsanPortEpEntry ::= SEQUENCE {
    cucsFabricFcVsanPortEpInstanceId                                 CucsManagedObjectId,
    cucsFabricFcVsanPortEpDn                                         CucsManagedObjectDn,
    cucsFabricFcVsanPortEpRn                                         SnmpAdminString,
    cucsFabricFcVsanPortEpAdminState                                 CucsFabricExternalEpAdminState,
    cucsFabricFcVsanPortEpChassisId                                  Gauge32,
    cucsFabricFcVsanPortEpEpDn                                       SnmpAdminString,
    cucsFabricFcVsanPortEpIfRole                                     CucsFabricSanEpIfRole,
    cucsFabricFcVsanPortEpIfType                                     CucsFabricPIoEpIfType,
    cucsFabricFcVsanPortEpLicGP                                      Unsigned64,
    cucsFabricFcVsanPortEpLicState                                   CucsLicenseState,
    cucsFabricFcVsanPortEpLocale                                     CucsFabricExternalEpLocale,
    cucsFabricFcVsanPortEpName                                       SnmpAdminString,
    cucsFabricFcVsanPortEpPeerDn                                     SnmpAdminString,
    cucsFabricFcVsanPortEpPeerPortId                                 Gauge32,
    cucsFabricFcVsanPortEpPeerSlotId                                 Gauge32,
    cucsFabricFcVsanPortEpPortId                                     CucsFabricFcVsanPortEpPortId,
    cucsFabricFcVsanPortEpSlotId                                     CucsFabricFcVsanPortEpSlotId,
    cucsFabricFcVsanPortEpSwitchId                                   CucsNetworkSwitchId,
    cucsFabricFcVsanPortEpTransport                                  CucsFabricAFcSanEpTransport,
    cucsFabricFcVsanPortEpType                                       CucsFabricSanEpType,
    cucsFabricFcVsanPortEpPeerChassisId                              Gauge32,
    cucsFabricFcVsanPortEpFltAggr                                    Unsigned64
}

cucsFabricFcVsanPortEpInstanceId OBJECT-TYPE
    SYNTAX       CucsManagedObjectId
    MAX-ACCESS   not-accessible
    STATUS       current
    DESCRIPTION
        "Instance identifier of the managed object."
    ::= { cucsFabricFcVsanPortEpEntry 1 }

cucsFabricFcVsanPortEpDn OBJECT-TYPE
    SYNTAX       CucsManagedObjectDn
    MAX-ACCESS   read-only
    STATUS       current
    DESCRIPTION
        "Cisco UCS fabric:FcVsanPortEp:dn managed object property"
    ::= { cucsFabricFcVsanPortEpEntry 2 }

cucsFabricFcVsanPortEpRn OBJECT-TYPE
    SYNTAX       SnmpAdminString
    MAX-ACCESS   read-only
    STATUS       current
    DESCRIPTION
        "Cisco UCS fabric:FcVsanPortEp:rn managed object property"
    ::= { cucsFabricFcVsanPortEpEntry 3 }

cucsFabricFcVsanPortEpAdminState OBJECT-TYPE
    SYNTAX       CucsFabricExternalEpAdminState
    MAX-ACCESS   read-only
    STATUS       current
    DESCRIPTION
        "Cisco UCS fabric:FcVsanPortEp:adminState managed object property"
    ::= { cucsFabricFcVsanPortEpEntry 4 }

cucsFabricFcVsanPortEpChassisId OBJECT-TYPE
    SYNTAX       Gauge32
    MAX-ACCESS   read-only
    STATUS       current
    DESCRIPTION
        "Cisco UCS fabric:FcVsanPortEp:chassisId managed object property"
    ::= { cucsFabricFcVsanPortEpEntry 5 }

cucsFabricFcVsanPortEpEpDn OBJECT-TYPE
    SYNTAX       SnmpAdminString
    MAX-ACCESS   read-only
    STATUS       current
    DESCRIPTION
        "Cisco UCS fabric:FcVsanPortEp:epDn managed object property"
    ::= { cucsFabricFcVsanPortEpEntry 6 }

cucsFabricFcVsanPortEpIfRole OBJECT-TYPE
    SYNTAX       CucsFabricSanEpIfRole
    MAX-ACCESS   read-only
    STATUS       current
    DESCRIPTION
        "Cisco UCS fabric:FcVsanPortEp:ifRole managed object property"
    ::= { cucsFabricFcVsanPortEpEntry 7 }

cucsFabricFcVsanPortEpIfType OBJECT-TYPE
    SYNTAX       CucsFabricPIoEpIfType
    MAX-ACCESS   read-only
    STATUS       current
    DESCRIPTION
        "Cisco UCS fabric:FcVsanPortEp:ifType managed object property"
    ::= { cucsFabricFcVsanPortEpEntry 8 }

cucsFabricFcVsanPortEpLicGP OBJECT-TYPE
    SYNTAX       Unsigned64
    MAX-ACCESS   read-only
    STATUS       current
    DESCRIPTION
        "Cisco UCS fabric:FcVsanPortEp:licGP managed object property"
    ::= { cucsFabricFcVsanPortEpEntry 9 }

cucsFabricFcVsanPortEpLicState OBJECT-TYPE
    SYNTAX       CucsLicenseState
    MAX-ACCESS   read-only
    STATUS       current
    DESCRIPTION
        "Cisco UCS fabric:FcVsanPortEp:licState managed object property"
    ::= { cucsFabricFcVsanPortEpEntry 10 }

cucsFabricFcVsanPortEpLocale OBJECT-TYPE
    SYNTAX       CucsFabricExternalEpLocale
    MAX-ACCESS   read-only
    STATUS       current
    DESCRIPTION
        "Cisco UCS fabric:FcVsanPortEp:locale managed object property"
    ::= { cucsFabricFcVsanPortEpEntry 11 }

cucsFabricFcVsanPortEpName OBJECT-TYPE
    SYNTAX       SnmpAdminString
    MAX-ACCESS   read-only
    STATUS       current
    DESCRIPTION
        "Cisco UCS fabric:FcVsanPortEp:name managed object property"
    ::= { cucsFabricFcVsanPortEpEntry 12 }

cucsFabricFcVsanPortEpPeerDn OBJECT-TYPE
    SYNTAX       SnmpAdminString
    MAX-ACCESS   read-only
    STATUS       current
    DESCRIPTION
        "Cisco UCS fabric:FcVsanPortEp:peerDn managed object property"
    ::= { cucsFabricFcVsanPortEpEntry 13 }

cucsFabricFcVsanPortEpPeerPortId OBJECT-TYPE
    SYNTAX       Gauge32
    MAX-ACCESS   read-only
    STATUS       current
    DESCRIPTION
        "Cisco UCS fabric:FcVsanPortEp:peerPortId managed object property"
    ::= { cucsFabricFcVsanPortEpEntry 14 }

cucsFabricFcVsanPortEpPeerSlotId OBJECT-TYPE
    SYNTAX       Gauge32
    MAX-ACCESS   read-only
    STATUS       current
    DESCRIPTION
        "Cisco UCS fabric:FcVsanPortEp:peerSlotId managed object property"
    ::= { cucsFabricFcVsanPortEpEntry 15 }

cucsFabricFcVsanPortEpPortId OBJECT-TYPE
    SYNTAX       CucsFabricFcVsanPortEpPortId
    MAX-ACCESS   read-only
    STATUS       current
    DESCRIPTION
        "Cisco UCS fabric:FcVsanPortEp:portId managed object property"
    ::= { cucsFabricFcVsanPortEpEntry 16 }

cucsFabricFcVsanPortEpSlotId OBJECT-TYPE
    SYNTAX       CucsFabricFcVsanPortEpSlotId
    MAX-ACCESS   read-only
    STATUS       current
    DESCRIPTION
        "Cisco UCS fabric:FcVsanPortEp:slotId managed object property"
    ::= { cucsFabricFcVsanPortEpEntry 17 }

cucsFabricFcVsanPortEpSwitchId OBJECT-TYPE
    SYNTAX       CucsNetworkSwitchId
    MAX-ACCESS   read-only
    STATUS       current
    DESCRIPTION
        "Cisco UCS fabric:FcVsanPortEp:switchId managed object property"
    ::= { cucsFabricFcVsanPortEpEntry 18 }

cucsFabricFcVsanPortEpTransport OBJECT-TYPE
    SYNTAX       CucsFabricAFcSanEpTransport
    MAX-ACCESS   read-only
    STATUS       current
    DESCRIPTION
        "Cisco UCS fabric:FcVsanPortEp:transport managed object property"
    ::= { cucsFabricFcVsanPortEpEntry 19 }

cucsFabricFcVsanPortEpType OBJECT-TYPE
    SYNTAX       CucsFabricSanEpType
    MAX-ACCESS   read-only
    STATUS       current
    DESCRIPTION
        "Cisco UCS fabric:FcVsanPortEp:type managed object property"
    ::= { cucsFabricFcVsanPortEpEntry 20 }

cucsFabricFcVsanPortEpPeerChassisId OBJECT-TYPE
    SYNTAX       Gauge32
    MAX-ACCESS   read-only
    STATUS       current
    DESCRIPTION
        "Cisco UCS fabric:FcVsanPortEp:peerChassisId managed
        object property"
    ::= { cucsFabricFcVsanPortEpEntry 21 }

cucsFabricFcVsanPortEpFltAggr OBJECT-TYPE
    SYNTAX       Unsigned64
    MAX-ACCESS   read-only
    STATUS       current
    DESCRIPTION
        "Cisco UCS fabric:FcVsanPortEp:fltAggr managed object property"
    ::= { cucsFabricFcVsanPortEpEntry 22 }

cucsFabricFcoeEstcEpTable OBJECT-TYPE
    SYNTAX           SEQUENCE OF CucsFabricFcoeEstcEpEntry
    MAX-ACCESS       not-accessible
    STATUS           current
    DESCRIPTION
        "Cisco UCS fabric:FcoeEstcEp managed object table"
    ::= { cucsFabricObjects 40 }

cucsFabricFcoeEstcEpEntry OBJECT-TYPE
    SYNTAX           CucsFabricFcoeEstcEpEntry
    MAX-ACCESS       not-accessible
    STATUS           current
    DESCRIPTION
        "Entry for the cucsFabricFcoeEstcEpTable table."
    INDEX { cucsFabricFcoeEstcEpInstanceId }
    ::= { cucsFabricFcoeEstcEpTable 1 }

CucsFabricFcoeEstcEpEntry ::= SEQUENCE {
    cucsFabricFcoeEstcEpInstanceId                                   CucsManagedObjectId,
    cucsFabricFcoeEstcEpDn                                           CucsManagedObjectDn,
    cucsFabricFcoeEstcEpRn                                           SnmpAdminString,
    cucsFabricFcoeEstcEpAdminState                                   CucsFabricExternalEpAdminState,
    cucsFabricFcoeEstcEpChassisId                                    Gauge32,
    cucsFabricFcoeEstcEpConfigState                                  CucsFabricConfigState,
    cucsFabricFcoeEstcEpEpDn                                         SnmpAdminString,
    cucsFabricFcoeEstcEpIfRole                                       CucsFabricAFcoeEstcEpIfRole,
    cucsFabricFcoeEstcEpIfType                                       CucsFabricPIoEpIfType,
    cucsFabricFcoeEstcEpLicGP                                        Unsigned64,
    cucsFabricFcoeEstcEpLicState                                     CucsLicenseState,
    cucsFabricFcoeEstcEpLocale                                       CucsFabricExternalEpLocale,
    cucsFabricFcoeEstcEpName                                         SnmpAdminString,
    cucsFabricFcoeEstcEpPeerDn                                       SnmpAdminString,
    cucsFabricFcoeEstcEpPeerPortId                                   Gauge32,
    cucsFabricFcoeEstcEpPeerSlotId                                   Gauge32,
    cucsFabricFcoeEstcEpPortId                                       CucsFabricFcoeEstcEpPortId,
    cucsFabricFcoeEstcEpSlotId                                       CucsFabricFcoeEstcEpSlotId,
    cucsFabricFcoeEstcEpSwitchId                                     CucsNetworkSwitchId,
    cucsFabricFcoeEstcEpTransport                                    CucsFabricAFcoeEstcEpTransport,
    cucsFabricFcoeEstcEpType                                         CucsFabricAFcoeEstcEpType,
    cucsFabricFcoeEstcEpUsrLbl                                       SnmpAdminString,
    cucsFabricFcoeEstcEpPeerChassisId                                Gauge32,
    cucsFabricFcoeEstcEpFltAggr                                      Unsigned64
}

cucsFabricFcoeEstcEpInstanceId OBJECT-TYPE
    SYNTAX       CucsManagedObjectId
    MAX-ACCESS   not-accessible
    STATUS       current
    DESCRIPTION
        "Instance identifier of the managed object."
    ::= { cucsFabricFcoeEstcEpEntry 1 }

cucsFabricFcoeEstcEpDn OBJECT-TYPE
    SYNTAX       CucsManagedObjectDn
    MAX-ACCESS   read-only
    STATUS       current
    DESCRIPTION
        "Cisco UCS fabric:FcoeEstcEp:dn managed object property"
    ::= { cucsFabricFcoeEstcEpEntry 2 }

cucsFabricFcoeEstcEpRn OBJECT-TYPE
    SYNTAX       SnmpAdminString
    MAX-ACCESS   read-only
    STATUS       current
    DESCRIPTION
        "Cisco UCS fabric:FcoeEstcEp:rn managed object property"
    ::= { cucsFabricFcoeEstcEpEntry 3 }

cucsFabricFcoeEstcEpAdminState OBJECT-TYPE
    SYNTAX       CucsFabricExternalEpAdminState
    MAX-ACCESS   read-only
    STATUS       current
    DESCRIPTION
        "Cisco UCS fabric:FcoeEstcEp:adminState managed object property"
    ::= { cucsFabricFcoeEstcEpEntry 4 }

cucsFabricFcoeEstcEpChassisId OBJECT-TYPE
    SYNTAX       Gauge32
    MAX-ACCESS   read-only
    STATUS       current
    DESCRIPTION
        "Cisco UCS fabric:FcoeEstcEp:chassisId managed object property"
    ::= { cucsFabricFcoeEstcEpEntry 5 }

cucsFabricFcoeEstcEpConfigState OBJECT-TYPE
    SYNTAX       CucsFabricConfigState
    MAX-ACCESS   read-only
    STATUS       current
    DESCRIPTION
        "Cisco UCS fabric:FcoeEstcEp:configState managed object property"
    ::= { cucsFabricFcoeEstcEpEntry 6 }

cucsFabricFcoeEstcEpEpDn OBJECT-TYPE
    SYNTAX       SnmpAdminString
    MAX-ACCESS   read-only
    STATUS       current
    DESCRIPTION
        "Cisco UCS fabric:FcoeEstcEp:epDn managed object property"
    ::= { cucsFabricFcoeEstcEpEntry 7 }

cucsFabricFcoeEstcEpIfRole OBJECT-TYPE
    SYNTAX       CucsFabricAFcoeEstcEpIfRole
    MAX-ACCESS   read-only
    STATUS       current
    DESCRIPTION
        "Cisco UCS fabric:FcoeEstcEp:ifRole managed object property"
    ::= { cucsFabricFcoeEstcEpEntry 8 }

cucsFabricFcoeEstcEpIfType OBJECT-TYPE
    SYNTAX       CucsFabricPIoEpIfType
    MAX-ACCESS   read-only
    STATUS       current
    DESCRIPTION
        "Cisco UCS fabric:FcoeEstcEp:ifType managed object property"
    ::= { cucsFabricFcoeEstcEpEntry 9 }

cucsFabricFcoeEstcEpLicGP OBJECT-TYPE
    SYNTAX       Unsigned64
    MAX-ACCESS   read-only
    STATUS       current
    DESCRIPTION
        "Cisco UCS fabric:FcoeEstcEp:licGP managed object property"
    ::= { cucsFabricFcoeEstcEpEntry 10 }

cucsFabricFcoeEstcEpLicState OBJECT-TYPE
    SYNTAX       CucsLicenseState
    MAX-ACCESS   read-only
    STATUS       current
    DESCRIPTION
        "Cisco UCS fabric:FcoeEstcEp:licState managed object property"
    ::= { cucsFabricFcoeEstcEpEntry 11 }

cucsFabricFcoeEstcEpLocale OBJECT-TYPE
    SYNTAX       CucsFabricExternalEpLocale
    MAX-ACCESS   read-only
    STATUS       current
    DESCRIPTION
        "Cisco UCS fabric:FcoeEstcEp:locale managed object property"
    ::= { cucsFabricFcoeEstcEpEntry 12 }

cucsFabricFcoeEstcEpName OBJECT-TYPE
    SYNTAX       SnmpAdminString
    MAX-ACCESS   read-only
    STATUS       current
    DESCRIPTION
        "Cisco UCS fabric:FcoeEstcEp:name managed object property"
    ::= { cucsFabricFcoeEstcEpEntry 13 }

cucsFabricFcoeEstcEpPeerDn OBJECT-TYPE
    SYNTAX       SnmpAdminString
    MAX-ACCESS   read-only
    STATUS       current
    DESCRIPTION
        "Cisco UCS fabric:FcoeEstcEp:peerDn managed object property"
    ::= { cucsFabricFcoeEstcEpEntry 14 }

cucsFabricFcoeEstcEpPeerPortId OBJECT-TYPE
    SYNTAX       Gauge32
    MAX-ACCESS   read-only
    STATUS       current
    DESCRIPTION
        "Cisco UCS fabric:FcoeEstcEp:peerPortId managed object property"
    ::= { cucsFabricFcoeEstcEpEntry 15 }

cucsFabricFcoeEstcEpPeerSlotId OBJECT-TYPE
    SYNTAX       Gauge32
    MAX-ACCESS   read-only
    STATUS       current
    DESCRIPTION
        "Cisco UCS fabric:FcoeEstcEp:peerSlotId managed object property"
    ::= { cucsFabricFcoeEstcEpEntry 16 }

cucsFabricFcoeEstcEpPortId OBJECT-TYPE
    SYNTAX       CucsFabricFcoeEstcEpPortId
    MAX-ACCESS   read-only
    STATUS       current
    DESCRIPTION
        "Cisco UCS fabric:FcoeEstcEp:portId managed object property"
    ::= { cucsFabricFcoeEstcEpEntry 17 }

cucsFabricFcoeEstcEpSlotId OBJECT-TYPE
    SYNTAX       CucsFabricFcoeEstcEpSlotId
    MAX-ACCESS   read-only
    STATUS       current
    DESCRIPTION
        "Cisco UCS fabric:FcoeEstcEp:slotId managed object property"
    ::= { cucsFabricFcoeEstcEpEntry 18 }

cucsFabricFcoeEstcEpSwitchId OBJECT-TYPE
    SYNTAX       CucsNetworkSwitchId
    MAX-ACCESS   read-only
    STATUS       current
    DESCRIPTION
        "Cisco UCS fabric:FcoeEstcEp:switchId managed object property"
    ::= { cucsFabricFcoeEstcEpEntry 19 }

cucsFabricFcoeEstcEpTransport OBJECT-TYPE
    SYNTAX       CucsFabricAFcoeEstcEpTransport
    MAX-ACCESS   read-only
    STATUS       current
    DESCRIPTION
        "Cisco UCS fabric:FcoeEstcEp:transport managed object property"
    ::= { cucsFabricFcoeEstcEpEntry 20 }

cucsFabricFcoeEstcEpType OBJECT-TYPE
    SYNTAX       CucsFabricAFcoeEstcEpType
    MAX-ACCESS   read-only
    STATUS       current
    DESCRIPTION
        "Cisco UCS fabric:FcoeEstcEp:type managed object property"
    ::= { cucsFabricFcoeEstcEpEntry 21 }

cucsFabricFcoeEstcEpUsrLbl OBJECT-TYPE
    SYNTAX       SnmpAdminString
    MAX-ACCESS   read-only
    STATUS       current
    DESCRIPTION
        "Cisco UCS fabric:FcoeEstcEp:usrLbl managed object property"
    ::= { cucsFabricFcoeEstcEpEntry 22 }

cucsFabricFcoeEstcEpPeerChassisId OBJECT-TYPE
    SYNTAX       Gauge32
    MAX-ACCESS   read-only
    STATUS       current
    DESCRIPTION
        "Cisco UCS fabric:FcoeEstcEp:peerChassisId managed
        object property"
    ::= { cucsFabricFcoeEstcEpEntry 23 }

cucsFabricFcoeEstcEpFltAggr OBJECT-TYPE
    SYNTAX       Unsigned64
    MAX-ACCESS   read-only
    STATUS       current
    DESCRIPTION
        "Cisco UCS fabric:FcoeEstcEp:fltAggr managed object property"
    ::= { cucsFabricFcoeEstcEpEntry 24 }

cucsFabricFcoeVsanPortEpTable OBJECT-TYPE
    SYNTAX           SEQUENCE OF CucsFabricFcoeVsanPortEpEntry
    MAX-ACCESS       not-accessible
    STATUS           current
    DESCRIPTION
        "Cisco UCS fabric:FcoeVsanPortEp managed object table"
    ::= { cucsFabricObjects 64 }

cucsFabricFcoeVsanPortEpEntry OBJECT-TYPE
    SYNTAX           CucsFabricFcoeVsanPortEpEntry
    MAX-ACCESS       not-accessible
    STATUS           current
    DESCRIPTION
        "Entry for the cucsFabricFcoeVsanPortEpTable table."
    INDEX { cucsFabricFcoeVsanPortEpInstanceId }
    ::= { cucsFabricFcoeVsanPortEpTable 1 }

CucsFabricFcoeVsanPortEpEntry ::= SEQUENCE {
    cucsFabricFcoeVsanPortEpInstanceId                               CucsManagedObjectId,
    cucsFabricFcoeVsanPortEpDn                                       CucsManagedObjectDn,
    cucsFabricFcoeVsanPortEpRn                                       SnmpAdminString,
    cucsFabricFcoeVsanPortEpAdminState                               CucsFabricExternalEpAdminState,
    cucsFabricFcoeVsanPortEpChassisId                                Gauge32,
    cucsFabricFcoeVsanPortEpEpDn                                     SnmpAdminString,
    cucsFabricFcoeVsanPortEpIfRole                                   CucsFabricSanEpIfRole,
    cucsFabricFcoeVsanPortEpIfType                                   CucsFabricPIoEpIfType,
    cucsFabricFcoeVsanPortEpLicGP                                    Unsigned64,
    cucsFabricFcoeVsanPortEpLicState                                 CucsLicenseState,
    cucsFabricFcoeVsanPortEpLocale                                   CucsFabricExternalEpLocale,
    cucsFabricFcoeVsanPortEpName                                     SnmpAdminString,
    cucsFabricFcoeVsanPortEpPeerChassisId                            Gauge32,
    cucsFabricFcoeVsanPortEpPeerDn                                   SnmpAdminString,
    cucsFabricFcoeVsanPortEpPeerPortId                               Gauge32,
    cucsFabricFcoeVsanPortEpPeerSlotId                               Gauge32,
    cucsFabricFcoeVsanPortEpPortId                                   CucsFabricFcoeVsanPortEpPortId,
    cucsFabricFcoeVsanPortEpSlotId                                   CucsFabricFcoeVsanPortEpSlotId,
    cucsFabricFcoeVsanPortEpSwitchId                                 CucsNetworkSwitchId,
    cucsFabricFcoeVsanPortEpTransport                                CucsFabricAFcSanEpTransport,
    cucsFabricFcoeVsanPortEpType                                     CucsFabricSanEpType,
    cucsFabricFcoeVsanPortEpFltAggr                                  Unsigned64
}

cucsFabricFcoeVsanPortEpInstanceId OBJECT-TYPE
    SYNTAX       CucsManagedObjectId
    MAX-ACCESS   not-accessible
    STATUS       current
    DESCRIPTION
        "Instance identifier of the managed object."
    ::= { cucsFabricFcoeVsanPortEpEntry 1 }

cucsFabricFcoeVsanPortEpDn OBJECT-TYPE
    SYNTAX       CucsManagedObjectDn
    MAX-ACCESS   read-only
    STATUS       current
    DESCRIPTION
        "Cisco UCS fabric:FcoeVsanPortEp:dn managed object property"
    ::= { cucsFabricFcoeVsanPortEpEntry 2 }

cucsFabricFcoeVsanPortEpRn OBJECT-TYPE
    SYNTAX       SnmpAdminString
    MAX-ACCESS   read-only
    STATUS       current
    DESCRIPTION
        "Cisco UCS fabric:FcoeVsanPortEp:rn managed object property"
    ::= { cucsFabricFcoeVsanPortEpEntry 3 }

cucsFabricFcoeVsanPortEpAdminState OBJECT-TYPE
    SYNTAX       CucsFabricExternalEpAdminState
    MAX-ACCESS   read-only
    STATUS       current
    DESCRIPTION
        "Cisco UCS fabric:FcoeVsanPortEp:adminState managed
        object property"
    ::= { cucsFabricFcoeVsanPortEpEntry 4 }

cucsFabricFcoeVsanPortEpChassisId OBJECT-TYPE
    SYNTAX       Gauge32
    MAX-ACCESS   read-only
    STATUS       current
    DESCRIPTION
        "Cisco UCS fabric:FcoeVsanPortEp:chassisId managed
        object property"
    ::= { cucsFabricFcoeVsanPortEpEntry 5 }

cucsFabricFcoeVsanPortEpEpDn OBJECT-TYPE
    SYNTAX       SnmpAdminString
    MAX-ACCESS   read-only
    STATUS       current
    DESCRIPTION
        "Cisco UCS fabric:FcoeVsanPortEp:epDn managed object property"
    ::= { cucsFabricFcoeVsanPortEpEntry 6 }

cucsFabricFcoeVsanPortEpIfRole OBJECT-TYPE
    SYNTAX       CucsFabricSanEpIfRole
    MAX-ACCESS   read-only
    STATUS       current
    DESCRIPTION
        "Cisco UCS fabric:FcoeVsanPortEp:ifRole managed object property"
    ::= { cucsFabricFcoeVsanPortEpEntry 7 }

cucsFabricFcoeVsanPortEpIfType OBJECT-TYPE
    SYNTAX       CucsFabricPIoEpIfType
    MAX-ACCESS   read-only
    STATUS       current
    DESCRIPTION
        "Cisco UCS fabric:FcoeVsanPortEp:ifType managed object property"
    ::= { cucsFabricFcoeVsanPortEpEntry 8 }

cucsFabricFcoeVsanPortEpLicGP OBJECT-TYPE
    SYNTAX       Unsigned64
    MAX-ACCESS   read-only
    STATUS       current
    DESCRIPTION
        "Cisco UCS fabric:FcoeVsanPortEp:licGP managed object property"
    ::= { cucsFabricFcoeVsanPortEpEntry 9 }

cucsFabricFcoeVsanPortEpLicState OBJECT-TYPE
    SYNTAX       CucsLicenseState
    MAX-ACCESS   read-only
    STATUS       current
    DESCRIPTION
        "Cisco UCS fabric:FcoeVsanPortEp:licState managed object property"
    ::= { cucsFabricFcoeVsanPortEpEntry 10 }

cucsFabricFcoeVsanPortEpLocale OBJECT-TYPE
    SYNTAX       CucsFabricExternalEpLocale
    MAX-ACCESS   read-only
    STATUS       current
    DESCRIPTION
        "Cisco UCS fabric:FcoeVsanPortEp:locale managed object property"
    ::= { cucsFabricFcoeVsanPortEpEntry 11 }

cucsFabricFcoeVsanPortEpName OBJECT-TYPE
    SYNTAX       SnmpAdminString
    MAX-ACCESS   read-only
    STATUS       current
    DESCRIPTION
        "Cisco UCS fabric:FcoeVsanPortEp:name managed object property"
    ::= { cucsFabricFcoeVsanPortEpEntry 12 }

cucsFabricFcoeVsanPortEpPeerChassisId OBJECT-TYPE
    SYNTAX       Gauge32
    MAX-ACCESS   read-only
    STATUS       current
    DESCRIPTION
        "Cisco UCS fabric:FcoeVsanPortEp:peerChassisId
        managed object property"
    ::= { cucsFabricFcoeVsanPortEpEntry 13 }

cucsFabricFcoeVsanPortEpPeerDn OBJECT-TYPE
    SYNTAX       SnmpAdminString
    MAX-ACCESS   read-only
    STATUS       current
    DESCRIPTION
        "Cisco UCS fabric:FcoeVsanPortEp:peerDn managed object property"
    ::= { cucsFabricFcoeVsanPortEpEntry 14 }

cucsFabricFcoeVsanPortEpPeerPortId OBJECT-TYPE
    SYNTAX       Gauge32
    MAX-ACCESS   read-only
    STATUS       current
    DESCRIPTION
        "Cisco UCS fabric:FcoeVsanPortEp:peerPortId managed
        object property"
    ::= { cucsFabricFcoeVsanPortEpEntry 15 }

cucsFabricFcoeVsanPortEpPeerSlotId OBJECT-TYPE
    SYNTAX       Gauge32
    MAX-ACCESS   read-only
    STATUS       current
    DESCRIPTION
        "Cisco UCS fabric:FcoeVsanPortEp:peerSlotId managed
        object property"
    ::= { cucsFabricFcoeVsanPortEpEntry 16 }

cucsFabricFcoeVsanPortEpPortId OBJECT-TYPE
    SYNTAX       CucsFabricFcoeVsanPortEpPortId
    MAX-ACCESS   read-only
    STATUS       current
    DESCRIPTION
        "Cisco UCS fabric:FcoeVsanPortEp:portId managed object property"
    ::= { cucsFabricFcoeVsanPortEpEntry 17 }

cucsFabricFcoeVsanPortEpSlotId OBJECT-TYPE
    SYNTAX       CucsFabricFcoeVsanPortEpSlotId
    MAX-ACCESS   read-only
    STATUS       current
    DESCRIPTION
        "Cisco UCS fabric:FcoeVsanPortEp:slotId managed object property"
    ::= { cucsFabricFcoeVsanPortEpEntry 18 }

cucsFabricFcoeVsanPortEpSwitchId OBJECT-TYPE
    SYNTAX       CucsNetworkSwitchId
    MAX-ACCESS   read-only
    STATUS       current
    DESCRIPTION
        "Cisco UCS fabric:FcoeVsanPortEp:switchId managed object property"
    ::= { cucsFabricFcoeVsanPortEpEntry 19 }

cucsFabricFcoeVsanPortEpTransport OBJECT-TYPE
    SYNTAX       CucsFabricAFcSanEpTransport
    MAX-ACCESS   read-only
    STATUS       current
    DESCRIPTION
        "Cisco UCS fabric:FcoeVsanPortEp:transport managed
        object property"
    ::= { cucsFabricFcoeVsanPortEpEntry 20 }

cucsFabricFcoeVsanPortEpType OBJECT-TYPE
    SYNTAX       CucsFabricSanEpType
    MAX-ACCESS   read-only
    STATUS       current
    DESCRIPTION
        "Cisco UCS fabric:FcoeVsanPortEp:type managed object property"
    ::= { cucsFabricFcoeVsanPortEpEntry 21 }

cucsFabricFcoeVsanPortEpFltAggr OBJECT-TYPE
    SYNTAX       Unsigned64
    MAX-ACCESS   read-only
    STATUS       current
    DESCRIPTION
        "Cisco UCS fabric:FcoeVsanPortEp:fltAggr managed object property"
    ::= { cucsFabricFcoeVsanPortEpEntry 22 }

cucsFabricIfTable OBJECT-TYPE
    SYNTAX           SEQUENCE OF CucsFabricIfEntry
    MAX-ACCESS       not-accessible
    STATUS           current
    DESCRIPTION
        "Cisco UCS fabric:If managed object table"
    ::= { cucsFabricObjects 41 }

cucsFabricIfEntry OBJECT-TYPE
    SYNTAX           CucsFabricIfEntry
    MAX-ACCESS       not-accessible
    STATUS           current
    DESCRIPTION
        "Entry for the cucsFabricIfTable table."
    INDEX { cucsFabricIfInstanceId }
    ::= { cucsFabricIfTable 1 }

CucsFabricIfEntry ::= SEQUENCE {
    cucsFabricIfInstanceId                                           CucsManagedObjectId,
    cucsFabricIfDn                                                   CucsManagedObjectDn,
    cucsFabricIfRn                                                   SnmpAdminString,
    cucsFabricIfAddr                                                 InetAddressIPv4,
    cucsFabricIfId                                                   CucsNetworkSwitchId
}

cucsFabricIfInstanceId OBJECT-TYPE
    SYNTAX       CucsManagedObjectId
    MAX-ACCESS   not-accessible
    STATUS       current
    DESCRIPTION
        "Instance identifier of the managed object."
    ::= { cucsFabricIfEntry 1 }

cucsFabricIfDn OBJECT-TYPE
    SYNTAX       CucsManagedObjectDn
    MAX-ACCESS   read-only
    STATUS       current
    DESCRIPTION
        "Cisco UCS fabric:If:dn managed object property"
    ::= { cucsFabricIfEntry 2 }

cucsFabricIfRn OBJECT-TYPE
    SYNTAX       SnmpAdminString
    MAX-ACCESS   read-only
    STATUS       current
    DESCRIPTION
        "Cisco UCS fabric:If:rn managed object property"
    ::= { cucsFabricIfEntry 3 }

cucsFabricIfAddr OBJECT-TYPE
    SYNTAX       InetAddressIPv4
    MAX-ACCESS   read-only
    STATUS       current
    DESCRIPTION
        "Cisco UCS fabric:If:addr managed object property"
    ::= { cucsFabricIfEntry 4 }

cucsFabricIfId OBJECT-TYPE
    SYNTAX       CucsNetworkSwitchId
    MAX-ACCESS   read-only
    STATUS       current
    DESCRIPTION
        "Cisco UCS fabric:If:id managed object property"
    ::= { cucsFabricIfEntry 5 }

cucsFabricLanCloudTable OBJECT-TYPE
    SYNTAX           SEQUENCE OF CucsFabricLanCloudEntry
    MAX-ACCESS       not-accessible
    STATUS           current
    DESCRIPTION
        "Cisco UCS fabric:LanCloud managed object table"
    ::= { cucsFabricObjects 42 }

cucsFabricLanCloudEntry OBJECT-TYPE
    SYNTAX           CucsFabricLanCloudEntry
    MAX-ACCESS       not-accessible
    STATUS           current
    DESCRIPTION
        "Entry for the cucsFabricLanCloudTable table."
    INDEX { cucsFabricLanCloudInstanceId }
    ::= { cucsFabricLanCloudTable 1 }

CucsFabricLanCloudEntry ::= SEQUENCE {
    cucsFabricLanCloudInstanceId                                     CucsManagedObjectId,
    cucsFabricLanCloudDn                                             CucsManagedObjectDn,
    cucsFabricLanCloudRn                                             SnmpAdminString,
    cucsFabricLanCloudFsmDescr                                       SnmpAdminString,
    cucsFabricLanCloudFsmPrev                                        SnmpAdminString,
    cucsFabricLanCloudFsmProgr                                       Gauge32,
    cucsFabricLanCloudFsmRmtInvErrCode                               Gauge32,
    cucsFabricLanCloudFsmRmtInvErrDescr                              SnmpAdminString,
    cucsFabricLanCloudFsmRmtInvRslt                                  CucsConditionRemoteInvRslt,
    cucsFabricLanCloudFsmStageDescr                                  SnmpAdminString,
    cucsFabricLanCloudFsmStamp                                       DateAndTime,
    cucsFabricLanCloudFsmStatus                                      SnmpAdminString,
    cucsFabricLanCloudFsmTry                                         Gauge32,
    cucsFabricLanCloudMacAging                                       TimeIntervalSec,
    cucsFabricLanCloudMode                                           CucsFabricSwitchingMode
}

cucsFabricLanCloudInstanceId OBJECT-TYPE
    SYNTAX       CucsManagedObjectId
    MAX-ACCESS   not-accessible
    STATUS       current
    DESCRIPTION
        "Instance identifier of the managed object."
    ::= { cucsFabricLanCloudEntry 1 }

cucsFabricLanCloudDn OBJECT-TYPE
    SYNTAX       CucsManagedObjectDn
    MAX-ACCESS   read-only
    STATUS       current
    DESCRIPTION
        "Cisco UCS fabric:LanCloud:dn managed object property"
    ::= { cucsFabricLanCloudEntry 2 }

cucsFabricLanCloudRn OBJECT-TYPE
    SYNTAX       SnmpAdminString
    MAX-ACCESS   read-only
    STATUS       current
    DESCRIPTION
        "Cisco UCS fabric:LanCloud:rn managed object property"
    ::= { cucsFabricLanCloudEntry 3 }

cucsFabricLanCloudFsmDescr OBJECT-TYPE
    SYNTAX       SnmpAdminString
    MAX-ACCESS   read-only
    STATUS       current
    DESCRIPTION
        "Cisco UCS fabric:LanCloud:fsmDescr managed object property"
    ::= { cucsFabricLanCloudEntry 4 }

cucsFabricLanCloudFsmPrev OBJECT-TYPE
    SYNTAX       SnmpAdminString
    MAX-ACCESS   read-only
    STATUS       current
    DESCRIPTION
        "Cisco UCS fabric:LanCloud:fsmPrev managed object property"
    ::= { cucsFabricLanCloudEntry 5 }

cucsFabricLanCloudFsmProgr OBJECT-TYPE
    SYNTAX       Gauge32
    MAX-ACCESS   read-only
    STATUS       current
    DESCRIPTION
        "Cisco UCS fabric:LanCloud:fsmProgr managed object property"
    ::= { cucsFabricLanCloudEntry 6 }

cucsFabricLanCloudFsmRmtInvErrCode OBJECT-TYPE
    SYNTAX       Gauge32
    MAX-ACCESS   read-only
    STATUS       current
    DESCRIPTION
        "Cisco UCS fabric:LanCloud:fsmRmtInvErrCode managed
        object property"
    ::= { cucsFabricLanCloudEntry 7 }

cucsFabricLanCloudFsmRmtInvErrDescr OBJECT-TYPE
    SYNTAX       SnmpAdminString
    MAX-ACCESS   read-only
    STATUS       current
    DESCRIPTION
        "Cisco UCS fabric:LanCloud:fsmRmtInvErrDescr managed
        object property"
    ::= { cucsFabricLanCloudEntry 8 }

cucsFabricLanCloudFsmRmtInvRslt OBJECT-TYPE
    SYNTAX       CucsConditionRemoteInvRslt
    MAX-ACCESS   read-only
    STATUS       current
    DESCRIPTION
        "Cisco UCS fabric:LanCloud:fsmRmtInvRslt managed object property"
    ::= { cucsFabricLanCloudEntry 9 }

cucsFabricLanCloudFsmStageDescr OBJECT-TYPE
    SYNTAX       SnmpAdminString
    MAX-ACCESS   read-only
    STATUS       current
    DESCRIPTION
        "Cisco UCS fabric:LanCloud:fsmStageDescr managed object property"
    ::= { cucsFabricLanCloudEntry 10 }

cucsFabricLanCloudFsmStamp OBJECT-TYPE
    SYNTAX       DateAndTime
    MAX-ACCESS   read-only
    STATUS       current
    DESCRIPTION
        "Cisco UCS fabric:LanCloud:fsmStamp managed object property"
    ::= { cucsFabricLanCloudEntry 11 }

cucsFabricLanCloudFsmStatus OBJECT-TYPE
    SYNTAX       SnmpAdminString
    MAX-ACCESS   read-only
    STATUS       current
    DESCRIPTION
        "Cisco UCS fabric:LanCloud:fsmStatus managed object property"
    ::= { cucsFabricLanCloudEntry 12 }

cucsFabricLanCloudFsmTry OBJECT-TYPE
    SYNTAX       Gauge32
    MAX-ACCESS   read-only
    STATUS       current
    DESCRIPTION
        "Cisco UCS fabric:LanCloud:fsmTry managed object property"
    ::= { cucsFabricLanCloudEntry 13 }

cucsFabricLanCloudMacAging OBJECT-TYPE
    SYNTAX       TimeIntervalSec
    MAX-ACCESS   read-only
    STATUS       current
    DESCRIPTION
        "Cisco UCS fabric:LanCloud:macAging managed object property"
    ::= { cucsFabricLanCloudEntry 14 }

cucsFabricLanCloudMode OBJECT-TYPE
    SYNTAX       CucsFabricSwitchingMode
    MAX-ACCESS   read-only
    STATUS       current
    DESCRIPTION
        "Cisco UCS fabric:LanCloud:mode managed object property"
    ::= { cucsFabricLanCloudEntry 15 }

cucsFabricLanCloudFsmTaskTable OBJECT-TYPE
    SYNTAX           SEQUENCE OF CucsFabricLanCloudFsmTaskEntry
    MAX-ACCESS       not-accessible
    STATUS           current
    DESCRIPTION
        "Cisco UCS fabric:LanCloudFsmTask managed object table"
    ::= { cucsFabricObjects 43 }

cucsFabricLanCloudFsmTaskEntry OBJECT-TYPE
    SYNTAX           CucsFabricLanCloudFsmTaskEntry
    MAX-ACCESS       not-accessible
    STATUS           current
    DESCRIPTION
        "Entry for the cucsFabricLanCloudFsmTaskTable table."
    INDEX { cucsFabricLanCloudFsmTaskInstanceId }
    ::= { cucsFabricLanCloudFsmTaskTable 1 }

CucsFabricLanCloudFsmTaskEntry ::= SEQUENCE {
    cucsFabricLanCloudFsmTaskInstanceId                              CucsManagedObjectId,
    cucsFabricLanCloudFsmTaskDn                                      CucsManagedObjectDn,
    cucsFabricLanCloudFsmTaskRn                                      SnmpAdminString,
    cucsFabricLanCloudFsmTaskCompletion                              CucsFsmCompletion,
    cucsFabricLanCloudFsmTaskFlags                                   CucsFsmFlags,
    cucsFabricLanCloudFsmTaskItem                                    CucsFabricLanCloudFsmTaskItem,
    cucsFabricLanCloudFsmTaskSeqId                                   Gauge32
}

cucsFabricLanCloudFsmTaskInstanceId OBJECT-TYPE
    SYNTAX       CucsManagedObjectId
    MAX-ACCESS   not-accessible
    STATUS       current
    DESCRIPTION
        "Instance identifier of the managed object."
    ::= { cucsFabricLanCloudFsmTaskEntry 1 }

cucsFabricLanCloudFsmTaskDn OBJECT-TYPE
    SYNTAX       CucsManagedObjectDn
    MAX-ACCESS   read-only
    STATUS       current
    DESCRIPTION
        "Cisco UCS fabric:LanCloudFsmTask:dn managed object property"
    ::= { cucsFabricLanCloudFsmTaskEntry 2 }

cucsFabricLanCloudFsmTaskRn OBJECT-TYPE
    SYNTAX       SnmpAdminString
    MAX-ACCESS   read-only
    STATUS       current
    DESCRIPTION
        "Cisco UCS fabric:LanCloudFsmTask:rn managed object property"
    ::= { cucsFabricLanCloudFsmTaskEntry 3 }

cucsFabricLanCloudFsmTaskCompletion OBJECT-TYPE
    SYNTAX       CucsFsmCompletion
    MAX-ACCESS   read-only
    STATUS       current
    DESCRIPTION
        "Cisco UCS fabric:LanCloudFsmTask:completion managed
        object property"
    ::= { cucsFabricLanCloudFsmTaskEntry 4 }

cucsFabricLanCloudFsmTaskFlags OBJECT-TYPE
    SYNTAX       CucsFsmFlags
    MAX-ACCESS   read-only
    STATUS       current
    DESCRIPTION
        "Cisco UCS fabric:LanCloudFsmTask:flags managed object property"
    ::= { cucsFabricLanCloudFsmTaskEntry 5 }

cucsFabricLanCloudFsmTaskItem OBJECT-TYPE
    SYNTAX       CucsFabricLanCloudFsmTaskItem
    MAX-ACCESS   read-only
    STATUS       current
    DESCRIPTION
        "Cisco UCS fabric:LanCloudFsmTask:item managed object property"
    ::= { cucsFabricLanCloudFsmTaskEntry 6 }

cucsFabricLanCloudFsmTaskSeqId OBJECT-TYPE
    SYNTAX       Gauge32
    MAX-ACCESS   read-only
    STATUS       current
    DESCRIPTION
        "Cisco UCS fabric:LanCloudFsmTask:seqId managed object property"
    ::= { cucsFabricLanCloudFsmTaskEntry 7 }

cucsFabricLanMonCloudTable OBJECT-TYPE
    SYNTAX           SEQUENCE OF CucsFabricLanMonCloudEntry
    MAX-ACCESS       not-accessible
    STATUS           current
    DESCRIPTION
        "Cisco UCS fabric:LanMonCloud managed object table"
    ::= { cucsFabricObjects 44 }

cucsFabricLanMonCloudEntry OBJECT-TYPE
    SYNTAX           CucsFabricLanMonCloudEntry
    MAX-ACCESS       not-accessible
    STATUS           current
    DESCRIPTION
        "Entry for the cucsFabricLanMonCloudTable table."
    INDEX { cucsFabricLanMonCloudInstanceId }
    ::= { cucsFabricLanMonCloudTable 1 }

CucsFabricLanMonCloudEntry ::= SEQUENCE {
    cucsFabricLanMonCloudInstanceId                                  CucsManagedObjectId,
    cucsFabricLanMonCloudDn                                          CucsManagedObjectDn,
    cucsFabricLanMonCloudRn                                          SnmpAdminString,
    cucsFabricLanMonCloudMode                                        CucsFabricSwitchingMode
}

cucsFabricLanMonCloudInstanceId OBJECT-TYPE
    SYNTAX       CucsManagedObjectId
    MAX-ACCESS   not-accessible
    STATUS       current
    DESCRIPTION
        "Instance identifier of the managed object."
    ::= { cucsFabricLanMonCloudEntry 1 }

cucsFabricLanMonCloudDn OBJECT-TYPE
    SYNTAX       CucsManagedObjectDn
    MAX-ACCESS   read-only
    STATUS       current
    DESCRIPTION
        "Cisco UCS fabric:LanMonCloud:dn managed object property"
    ::= { cucsFabricLanMonCloudEntry 2 }

cucsFabricLanMonCloudRn OBJECT-TYPE
    SYNTAX       SnmpAdminString
    MAX-ACCESS   read-only
    STATUS       current
    DESCRIPTION
        "Cisco UCS fabric:LanMonCloud:rn managed object property"
    ::= { cucsFabricLanMonCloudEntry 3 }

cucsFabricLanMonCloudMode OBJECT-TYPE
    SYNTAX       CucsFabricSwitchingMode
    MAX-ACCESS   read-only
    STATUS       current
    DESCRIPTION
        "Cisco UCS fabric:LanMonCloud:mode managed object property"
    ::= { cucsFabricLanMonCloudEntry 4 }

cucsFabricLanPinGroupTable OBJECT-TYPE
    SYNTAX           SEQUENCE OF CucsFabricLanPinGroupEntry
    MAX-ACCESS       not-accessible
    STATUS           current
    DESCRIPTION
        "Cisco UCS fabric:LanPinGroup managed object table"
    ::= { cucsFabricObjects 45 }

cucsFabricLanPinGroupEntry OBJECT-TYPE
    SYNTAX           CucsFabricLanPinGroupEntry
    MAX-ACCESS       not-accessible
    STATUS           current
    DESCRIPTION
        "Entry for the cucsFabricLanPinGroupTable table."
    INDEX { cucsFabricLanPinGroupInstanceId }
    ::= { cucsFabricLanPinGroupTable 1 }

CucsFabricLanPinGroupEntry ::= SEQUENCE {
    cucsFabricLanPinGroupInstanceId                                  CucsManagedObjectId,
    cucsFabricLanPinGroupDn                                          CucsManagedObjectDn,
    cucsFabricLanPinGroupRn                                          SnmpAdminString,
    cucsFabricLanPinGroupDescr                                       SnmpAdminString,
    cucsFabricLanPinGroupIntId                                       SnmpAdminString,
    cucsFabricLanPinGroupName                                        SnmpAdminString,
    cucsFabricLanPinGroupSize                                        Gauge32
}

cucsFabricLanPinGroupInstanceId OBJECT-TYPE
    SYNTAX       CucsManagedObjectId
    MAX-ACCESS   not-accessible
    STATUS       current
    DESCRIPTION
        "Instance identifier of the managed object."
    ::= { cucsFabricLanPinGroupEntry 1 }

cucsFabricLanPinGroupDn OBJECT-TYPE
    SYNTAX       CucsManagedObjectDn
    MAX-ACCESS   read-only
    STATUS       current
    DESCRIPTION
        "Cisco UCS fabric:LanPinGroup:dn managed object property"
    ::= { cucsFabricLanPinGroupEntry 2 }

cucsFabricLanPinGroupRn OBJECT-TYPE
    SYNTAX       SnmpAdminString
    MAX-ACCESS   read-only
    STATUS       current
    DESCRIPTION
        "Cisco UCS fabric:LanPinGroup:rn managed object property"
    ::= { cucsFabricLanPinGroupEntry 3 }

cucsFabricLanPinGroupDescr OBJECT-TYPE
    SYNTAX       SnmpAdminString
    MAX-ACCESS   read-only
    STATUS       current
    DESCRIPTION
        "Cisco UCS fabric:LanPinGroup:descr managed object property"
    ::= { cucsFabricLanPinGroupEntry 4 }

cucsFabricLanPinGroupIntId OBJECT-TYPE
    SYNTAX       SnmpAdminString
    MAX-ACCESS   read-only
    STATUS       current
    DESCRIPTION
        "Cisco UCS fabric:LanPinGroup:intId managed object property"
    ::= { cucsFabricLanPinGroupEntry 5 }

cucsFabricLanPinGroupName OBJECT-TYPE
    SYNTAX       SnmpAdminString
    MAX-ACCESS   read-only
    STATUS       current
    DESCRIPTION
        "Cisco UCS fabric:LanPinGroup:name managed object property"
    ::= { cucsFabricLanPinGroupEntry 6 }

cucsFabricLanPinGroupSize OBJECT-TYPE
    SYNTAX       Gauge32
    MAX-ACCESS   read-only
    STATUS       current
    DESCRIPTION
        "Cisco UCS fabric:LanPinGroup:size managed object property"
    ::= { cucsFabricLanPinGroupEntry 7 }

cucsFabricLanPinTargetTable OBJECT-TYPE
    SYNTAX           SEQUENCE OF CucsFabricLanPinTargetEntry
    MAX-ACCESS       not-accessible
    STATUS           current
    DESCRIPTION
        "Cisco UCS fabric:LanPinTarget managed object table"
    ::= { cucsFabricObjects 46 }

cucsFabricLanPinTargetEntry OBJECT-TYPE
    SYNTAX           CucsFabricLanPinTargetEntry
    MAX-ACCESS       not-accessible
    STATUS           current
    DESCRIPTION
        "Entry for the cucsFabricLanPinTargetTable table."
    INDEX { cucsFabricLanPinTargetInstanceId }
    ::= { cucsFabricLanPinTargetTable 1 }

CucsFabricLanPinTargetEntry ::= SEQUENCE {
    cucsFabricLanPinTargetInstanceId                                 CucsManagedObjectId,
    cucsFabricLanPinTargetDn                                         CucsManagedObjectDn,
    cucsFabricLanPinTargetRn                                         SnmpAdminString,
    cucsFabricLanPinTargetEpDn                                       SnmpAdminString,
    cucsFabricLanPinTargetFabricId                                   SnmpAdminString
}

cucsFabricLanPinTargetInstanceId OBJECT-TYPE
    SYNTAX       CucsManagedObjectId
    MAX-ACCESS   not-accessible
    STATUS       current
    DESCRIPTION
        "Instance identifier of the managed object."
    ::= { cucsFabricLanPinTargetEntry 1 }

cucsFabricLanPinTargetDn OBJECT-TYPE
    SYNTAX       CucsManagedObjectDn
    MAX-ACCESS   read-only
    STATUS       current
    DESCRIPTION
        "Cisco UCS fabric:LanPinTarget:dn managed object property"
    ::= { cucsFabricLanPinTargetEntry 2 }

cucsFabricLanPinTargetRn OBJECT-TYPE
    SYNTAX       SnmpAdminString
    MAX-ACCESS   read-only
    STATUS       current
    DESCRIPTION
        "Cisco UCS fabric:LanPinTarget:rn managed object property"
    ::= { cucsFabricLanPinTargetEntry 3 }

cucsFabricLanPinTargetEpDn OBJECT-TYPE
    SYNTAX       SnmpAdminString
    MAX-ACCESS   read-only
    STATUS       current
    DESCRIPTION
        "Cisco UCS fabric:LanPinTarget:epDn managed object property"
    ::= { cucsFabricLanPinTargetEntry 4 }

cucsFabricLanPinTargetFabricId OBJECT-TYPE
    SYNTAX       SnmpAdminString
    MAX-ACCESS   read-only
    STATUS       current
    DESCRIPTION
        "Cisco UCS fabric:LanPinTarget:fabricId managed object property"
    ::= { cucsFabricLanPinTargetEntry 5 }

cucsFabricLastAckedSlotTable OBJECT-TYPE
    SYNTAX           SEQUENCE OF CucsFabricLastAckedSlotEntry
    MAX-ACCESS       not-accessible
    STATUS           current
    DESCRIPTION
        "Cisco UCS fabric:LastAckedSlot managed object table"
    ::= { cucsFabricObjects 47 }

cucsFabricLastAckedSlotEntry OBJECT-TYPE
    SYNTAX           CucsFabricLastAckedSlotEntry
    MAX-ACCESS       not-accessible
    STATUS           current
    DESCRIPTION
        "Entry for the cucsFabricLastAckedSlotTable table."
    INDEX { cucsFabricLastAckedSlotInstanceId }
    ::= { cucsFabricLastAckedSlotTable 1 }

CucsFabricLastAckedSlotEntry ::= SEQUENCE {
    cucsFabricLastAckedSlotInstanceId                                CucsManagedObjectId,
    cucsFabricLastAckedSlotDn                                        CucsManagedObjectDn,
    cucsFabricLastAckedSlotRn                                        SnmpAdminString,
    cucsFabricLastAckedSlotChassisId                                 Gauge32,
    cucsFabricLastAckedSlotSlotId                                    Gauge32,
    cucsFabricLastAckedSlotSwitchId                                  CucsNetworkSwitchId
}

cucsFabricLastAckedSlotInstanceId OBJECT-TYPE
    SYNTAX       CucsManagedObjectId
    MAX-ACCESS   not-accessible
    STATUS       current
    DESCRIPTION
        "Instance identifier of the managed object."
    ::= { cucsFabricLastAckedSlotEntry 1 }

cucsFabricLastAckedSlotDn OBJECT-TYPE
    SYNTAX       CucsManagedObjectDn
    MAX-ACCESS   read-only
    STATUS       current
    DESCRIPTION
        "Cisco UCS fabric:LastAckedSlot:dn managed object property"
    ::= { cucsFabricLastAckedSlotEntry 2 }

cucsFabricLastAckedSlotRn OBJECT-TYPE
    SYNTAX       SnmpAdminString
    MAX-ACCESS   read-only
    STATUS       current
    DESCRIPTION
        "Cisco UCS fabric:LastAckedSlot:rn managed object property"
    ::= { cucsFabricLastAckedSlotEntry 3 }

cucsFabricLastAckedSlotChassisId OBJECT-TYPE
    SYNTAX       Gauge32
    MAX-ACCESS   read-only
    STATUS       current
    DESCRIPTION
        "Cisco UCS fabric:LastAckedSlot:chassisId managed object property"
    ::= { cucsFabricLastAckedSlotEntry 4 }

cucsFabricLastAckedSlotSlotId OBJECT-TYPE
    SYNTAX       Gauge32
    MAX-ACCESS   read-only
    STATUS       current
    DESCRIPTION
        "Cisco UCS fabric:LastAckedSlot:slotId managed object property"
    ::= { cucsFabricLastAckedSlotEntry 5 }

cucsFabricLastAckedSlotSwitchId OBJECT-TYPE
    SYNTAX       CucsNetworkSwitchId
    MAX-ACCESS   read-only
    STATUS       current
    DESCRIPTION
        "Cisco UCS fabric:LastAckedSlot:switchId managed object property"
    ::= { cucsFabricLastAckedSlotEntry 6 }

cucsFabricLocaleTable OBJECT-TYPE
    SYNTAX           SEQUENCE OF CucsFabricLocaleEntry
    MAX-ACCESS       not-accessible
    STATUS           current
    DESCRIPTION
        "Cisco UCS fabric:Locale managed object table"
    ::= { cucsFabricObjects 48 }

cucsFabricLocaleEntry OBJECT-TYPE
    SYNTAX           CucsFabricLocaleEntry
    MAX-ACCESS       not-accessible
    STATUS           current
    DESCRIPTION
        "Entry for the cucsFabricLocaleTable table."
    INDEX { cucsFabricLocaleInstanceId }
    ::= { cucsFabricLocaleTable 1 }

CucsFabricLocaleEntry ::= SEQUENCE {
    cucsFabricLocaleInstanceId                                       CucsManagedObjectId,
    cucsFabricLocaleDn                                               CucsManagedObjectDn,
    cucsFabricLocaleRn                                               SnmpAdminString,
    cucsFabricLocaleCType                                            Gauge32,
    cucsFabricLocaleChassisId                                        Gauge32,
    cucsFabricLocaleLocale                                           CucsNetworkLocale,
    cucsFabricLocaleName                                             SnmpAdminString,
    cucsFabricLocaleSide                                             CucsNetworkSide,
    cucsFabricLocaleSlotId                                           Gauge32,
    cucsFabricLocaleSwitchId                                         CucsNetworkSwitchId,
    cucsFabricLocaleTransport                                        CucsNetworkTransport,
    cucsFabricLocaleType                                             CucsNetworkConnectionType
}

cucsFabricLocaleInstanceId OBJECT-TYPE
    SYNTAX       CucsManagedObjectId
    MAX-ACCESS   not-accessible
    STATUS       current
    DESCRIPTION
        "Instance identifier of the managed object."
    ::= { cucsFabricLocaleEntry 1 }

cucsFabricLocaleDn OBJECT-TYPE
    SYNTAX       CucsManagedObjectDn
    MAX-ACCESS   read-only
    STATUS       current
    DESCRIPTION
        "Cisco UCS fabric:Locale:dn managed object property"
    ::= { cucsFabricLocaleEntry 2 }

cucsFabricLocaleRn OBJECT-TYPE
    SYNTAX       SnmpAdminString
    MAX-ACCESS   read-only
    STATUS       current
    DESCRIPTION
        "Cisco UCS fabric:Locale:rn managed object property"
    ::= { cucsFabricLocaleEntry 3 }

cucsFabricLocaleCType OBJECT-TYPE
    SYNTAX       Gauge32
    MAX-ACCESS   read-only
    STATUS       current
    DESCRIPTION
        "Cisco UCS fabric:Locale:cType managed object property"
    ::= { cucsFabricLocaleEntry 4 }

cucsFabricLocaleChassisId OBJECT-TYPE
    SYNTAX       Gauge32
    MAX-ACCESS   read-only
    STATUS       current
    DESCRIPTION
        "Cisco UCS fabric:Locale:chassisId managed object property"
    ::= { cucsFabricLocaleEntry 5 }

cucsFabricLocaleLocale OBJECT-TYPE
    SYNTAX       CucsNetworkLocale
    MAX-ACCESS   read-only
    STATUS       current
    DESCRIPTION
        "Cisco UCS fabric:Locale:locale managed object property"
    ::= { cucsFabricLocaleEntry 6 }

cucsFabricLocaleName OBJECT-TYPE
    SYNTAX       SnmpAdminString
    MAX-ACCESS   read-only
    STATUS       current
    DESCRIPTION
        "Cisco UCS fabric:Locale:name managed object property"
    ::= { cucsFabricLocaleEntry 7 }

cucsFabricLocaleSide OBJECT-TYPE
    SYNTAX       CucsNetworkSide
    MAX-ACCESS   read-only
    STATUS       current
    DESCRIPTION
        "Cisco UCS fabric:Locale:side managed object property"
    ::= { cucsFabricLocaleEntry 8 }

cucsFabricLocaleSlotId OBJECT-TYPE
    SYNTAX       Gauge32
    MAX-ACCESS   read-only
    STATUS       current
    DESCRIPTION
        "Cisco UCS fabric:Locale:slotId managed object property"
    ::= { cucsFabricLocaleEntry 9 }

cucsFabricLocaleSwitchId OBJECT-TYPE
    SYNTAX       CucsNetworkSwitchId
    MAX-ACCESS   read-only
    STATUS       current
    DESCRIPTION
        "Cisco UCS fabric:Locale:switchId managed object property"
    ::= { cucsFabricLocaleEntry 10 }

cucsFabricLocaleTransport OBJECT-TYPE
    SYNTAX       CucsNetworkTransport
    MAX-ACCESS   read-only
    STATUS       current
    DESCRIPTION
        "Cisco UCS fabric:Locale:transport managed object property"
    ::= { cucsFabricLocaleEntry 11 }

cucsFabricLocaleType OBJECT-TYPE
    SYNTAX       CucsNetworkConnectionType
    MAX-ACCESS   read-only
    STATUS       current
    DESCRIPTION
        "Cisco UCS fabric:Locale:type managed object property"
    ::= { cucsFabricLocaleEntry 12 }

cucsFabricPathTable OBJECT-TYPE
    SYNTAX           SEQUENCE OF CucsFabricPathEntry
    MAX-ACCESS       not-accessible
    STATUS           current
    DESCRIPTION
        "Cisco UCS fabric:Path managed object table"
    ::= { cucsFabricObjects 49 }

cucsFabricPathEntry OBJECT-TYPE
    SYNTAX           CucsFabricPathEntry
    MAX-ACCESS       not-accessible
    STATUS           current
    DESCRIPTION
        "Entry for the cucsFabricPathTable table."
    INDEX { cucsFabricPathInstanceId }
    ::= { cucsFabricPathTable 1 }

CucsFabricPathEntry ::= SEQUENCE {
    cucsFabricPathInstanceId                                         CucsManagedObjectId,
    cucsFabricPathDn                                                 CucsManagedObjectDn,
    cucsFabricPathRn                                                 SnmpAdminString,
    cucsFabricPathCType                                              Gauge32,
    cucsFabricPathChassisId                                          Gauge32,
    cucsFabricPathEnacp                                              Gauge32,
    cucsFabricPathId                                                 Gauge32,
    cucsFabricPathLocale                                             CucsNetworkLocale,
    cucsFabricPathName                                               SnmpAdminString,
    cucsFabricPathNsSize                                             Gauge32,
    cucsFabricPathSide                                               CucsNetworkSide,
    cucsFabricPathSwitchId                                           CucsNetworkSwitchId,
    cucsFabricPathTransport                                          CucsNetworkTransport,
    cucsFabricPathType                                               CucsNetworkConnectionType
}

cucsFabricPathInstanceId OBJECT-TYPE
    SYNTAX       CucsManagedObjectId
    MAX-ACCESS   not-accessible
    STATUS       current
    DESCRIPTION
        "Instance identifier of the managed object."
    ::= { cucsFabricPathEntry 1 }

cucsFabricPathDn OBJECT-TYPE
    SYNTAX       CucsManagedObjectDn
    MAX-ACCESS   read-only
    STATUS       current
    DESCRIPTION
        "Cisco UCS fabric:Path:dn managed object property"
    ::= { cucsFabricPathEntry 2 }

cucsFabricPathRn OBJECT-TYPE
    SYNTAX       SnmpAdminString
    MAX-ACCESS   read-only
    STATUS       current
    DESCRIPTION
        "Cisco UCS fabric:Path:rn managed object property"
    ::= { cucsFabricPathEntry 3 }

cucsFabricPathCType OBJECT-TYPE
    SYNTAX       Gauge32
    MAX-ACCESS   read-only
    STATUS       current
    DESCRIPTION
        "Cisco UCS fabric:Path:cType managed object property"
    ::= { cucsFabricPathEntry 4 }

cucsFabricPathChassisId OBJECT-TYPE
    SYNTAX       Gauge32
    MAX-ACCESS   read-only
    STATUS       current
    DESCRIPTION
        "Cisco UCS fabric:Path:chassisId managed object property"
    ::= { cucsFabricPathEntry 5 }

cucsFabricPathEnacp OBJECT-TYPE
    SYNTAX       Gauge32
    MAX-ACCESS   read-only
    STATUS       current
    DESCRIPTION
        "Cisco UCS fabric:Path:enacp managed object property"
    ::= { cucsFabricPathEntry 6 }

cucsFabricPathId OBJECT-TYPE
    SYNTAX       Gauge32
    MAX-ACCESS   read-only
    STATUS       current
    DESCRIPTION
        "Cisco UCS fabric:Path:id managed object property"
    ::= { cucsFabricPathEntry 7 }

cucsFabricPathLocale OBJECT-TYPE
    SYNTAX       CucsNetworkLocale
    MAX-ACCESS   read-only
    STATUS       current
    DESCRIPTION
        "Cisco UCS fabric:Path:locale managed object property"
    ::= { cucsFabricPathEntry 8 }

cucsFabricPathName OBJECT-TYPE
    SYNTAX       SnmpAdminString
    MAX-ACCESS   read-only
    STATUS       current
    DESCRIPTION
        "Cisco UCS fabric:Path:name managed object property"
    ::= { cucsFabricPathEntry 9 }

cucsFabricPathNsSize OBJECT-TYPE
    SYNTAX       Gauge32
    MAX-ACCESS   read-only
    STATUS       current
    DESCRIPTION
        "Cisco UCS fabric:Path:nsSize managed object property"
    ::= { cucsFabricPathEntry 10 }

cucsFabricPathSide OBJECT-TYPE
    SYNTAX       CucsNetworkSide
    MAX-ACCESS   read-only
    STATUS       current
    DESCRIPTION
        "Cisco UCS fabric:Path:side managed object property"
    ::= { cucsFabricPathEntry 11 }

cucsFabricPathSwitchId OBJECT-TYPE
    SYNTAX       CucsNetworkSwitchId
    MAX-ACCESS   read-only
    STATUS       current
    DESCRIPTION
        "Cisco UCS fabric:Path:switchId managed object property"
    ::= { cucsFabricPathEntry 12 }

cucsFabricPathTransport OBJECT-TYPE
    SYNTAX       CucsNetworkTransport
    MAX-ACCESS   read-only
    STATUS       current
    DESCRIPTION
        "Cisco UCS fabric:Path:transport managed object property"
    ::= { cucsFabricPathEntry 13 }

cucsFabricPathType OBJECT-TYPE
    SYNTAX       CucsNetworkConnectionType
    MAX-ACCESS   read-only
    STATUS       current
    DESCRIPTION
        "Cisco UCS fabric:Path:type managed object property"
    ::= { cucsFabricPathEntry 14 }

cucsFabricPathConnTable OBJECT-TYPE
    SYNTAX           SEQUENCE OF CucsFabricPathConnEntry
    MAX-ACCESS       not-accessible
    STATUS           current
    DESCRIPTION
        "Cisco UCS fabric:PathConn managed object table"
    ::= { cucsFabricObjects 50 }

cucsFabricPathConnEntry OBJECT-TYPE
    SYNTAX           CucsFabricPathConnEntry
    MAX-ACCESS       not-accessible
    STATUS           current
    DESCRIPTION
        "Entry for the cucsFabricPathConnTable table."
    INDEX { cucsFabricPathConnInstanceId }
    ::= { cucsFabricPathConnTable 1 }

CucsFabricPathConnEntry ::= SEQUENCE {
    cucsFabricPathConnInstanceId                                     CucsManagedObjectId,
    cucsFabricPathConnDn                                             CucsManagedObjectDn,
    cucsFabricPathConnRn                                             SnmpAdminString,
    cucsFabricPathConnCType                                          Gauge32,
    cucsFabricPathConnLocale                                         CucsNetworkLocale,
    cucsFabricPathConnName                                           SnmpAdminString,
    cucsFabricPathConnTransport                                      CucsNetworkTransport,
    cucsFabricPathConnType                                           CucsNetworkConnectionType
}

cucsFabricPathConnInstanceId OBJECT-TYPE
    SYNTAX       CucsManagedObjectId
    MAX-ACCESS   not-accessible
    STATUS       current
    DESCRIPTION
        "Instance identifier of the managed object."
    ::= { cucsFabricPathConnEntry 1 }

cucsFabricPathConnDn OBJECT-TYPE
    SYNTAX       CucsManagedObjectDn
    MAX-ACCESS   read-only
    STATUS       current
    DESCRIPTION
        "Cisco UCS fabric:PathConn:dn managed object property"
    ::= { cucsFabricPathConnEntry 2 }

cucsFabricPathConnRn OBJECT-TYPE
    SYNTAX       SnmpAdminString
    MAX-ACCESS   read-only
    STATUS       current
    DESCRIPTION
        "Cisco UCS fabric:PathConn:rn managed object property"
    ::= { cucsFabricPathConnEntry 3 }

cucsFabricPathConnCType OBJECT-TYPE
    SYNTAX       Gauge32
    MAX-ACCESS   read-only
    STATUS       current
    DESCRIPTION
        "Cisco UCS fabric:PathConn:cType managed object property"
    ::= { cucsFabricPathConnEntry 4 }

cucsFabricPathConnLocale OBJECT-TYPE
    SYNTAX       CucsNetworkLocale
    MAX-ACCESS   read-only
    STATUS       current
    DESCRIPTION
        "Cisco UCS fabric:PathConn:locale managed object property"
    ::= { cucsFabricPathConnEntry 5 }

cucsFabricPathConnName OBJECT-TYPE
    SYNTAX       SnmpAdminString
    MAX-ACCESS   read-only
    STATUS       current
    DESCRIPTION
        "Cisco UCS fabric:PathConn:name managed object property"
    ::= { cucsFabricPathConnEntry 6 }

cucsFabricPathConnTransport OBJECT-TYPE
    SYNTAX       CucsNetworkTransport
    MAX-ACCESS   read-only
    STATUS       current
    DESCRIPTION
        "Cisco UCS fabric:PathConn:transport managed object property"
    ::= { cucsFabricPathConnEntry 7 }

cucsFabricPathConnType OBJECT-TYPE
    SYNTAX       CucsNetworkConnectionType
    MAX-ACCESS   read-only
    STATUS       current
    DESCRIPTION
        "Cisco UCS fabric:PathConn:type managed object property"
    ::= { cucsFabricPathConnEntry 8 }

cucsFabricPathEpTable OBJECT-TYPE
    SYNTAX           SEQUENCE OF CucsFabricPathEpEntry
    MAX-ACCESS       not-accessible
    STATUS           current
    DESCRIPTION
        "Cisco UCS fabric:PathEp managed object table"
    ::= { cucsFabricObjects 51 }

cucsFabricPathEpEntry OBJECT-TYPE
    SYNTAX           CucsFabricPathEpEntry
    MAX-ACCESS       not-accessible
    STATUS           current
    DESCRIPTION
        "Entry for the cucsFabricPathEpTable table."
    INDEX { cucsFabricPathEpInstanceId }
    ::= { cucsFabricPathEpTable 1 }

CucsFabricPathEpEntry ::= SEQUENCE {
    cucsFabricPathEpInstanceId                                       CucsManagedObjectId,
    cucsFabricPathEpDn                                               CucsManagedObjectDn,
    cucsFabricPathEpRn                                               SnmpAdminString,
    cucsFabricPathEpCType                                            Gauge32,
    cucsFabricPathEpChassisId                                        Gauge32,
    cucsFabricPathEpEpDn                                             SnmpAdminString,
    cucsFabricPathEpIfRole                                           CucsNetworkPortRole,
    cucsFabricPathEpIfType                                           CucsFabricPathEpIfType,
    cucsFabricPathEpLocale                                           CucsFabricPathEpLocale,
    cucsFabricPathEpName                                             SnmpAdminString,
    cucsFabricPathEpPeerDn                                           SnmpAdminString,
    cucsFabricPathEpPeerPortId                                       Gauge32,
    cucsFabricPathEpPeerSlotId                                       Gauge32,
    cucsFabricPathEpPortId                                           Gauge32,
    cucsFabricPathEpSide                                             CucsNetworkSide,
    cucsFabricPathEpSlotId                                           Gauge32,
    cucsFabricPathEpSwitchId                                         CucsNetworkSwitchId,
    cucsFabricPathEpTransport                                        CucsNetworkTransport,
    cucsFabricPathEpType                                             CucsNetworkConnectionType,
    cucsFabricPathEpDiagLldpTransmit                                 TruthValue,
    cucsFabricPathEpPeerChassisId                                    Gauge32,
    cucsFabricPathEpPeerMac                                          MacAddress
}

cucsFabricPathEpInstanceId OBJECT-TYPE
    SYNTAX       CucsManagedObjectId
    MAX-ACCESS   not-accessible
    STATUS       current
    DESCRIPTION
        "Instance identifier of the managed object."
    ::= { cucsFabricPathEpEntry 1 }

cucsFabricPathEpDn OBJECT-TYPE
    SYNTAX       CucsManagedObjectDn
    MAX-ACCESS   read-only
    STATUS       current
    DESCRIPTION
        "Cisco UCS fabric:PathEp:dn managed object property"
    ::= { cucsFabricPathEpEntry 2 }

cucsFabricPathEpRn OBJECT-TYPE
    SYNTAX       SnmpAdminString
    MAX-ACCESS   read-only
    STATUS       current
    DESCRIPTION
        "Cisco UCS fabric:PathEp:rn managed object property"
    ::= { cucsFabricPathEpEntry 3 }

cucsFabricPathEpCType OBJECT-TYPE
    SYNTAX       Gauge32
    MAX-ACCESS   read-only
    STATUS       current
    DESCRIPTION
        "Cisco UCS fabric:PathEp:cType managed object property"
    ::= { cucsFabricPathEpEntry 4 }

cucsFabricPathEpChassisId OBJECT-TYPE
    SYNTAX       Gauge32
    MAX-ACCESS   read-only
    STATUS       current
    DESCRIPTION
        "Cisco UCS fabric:PathEp:chassisId managed object property"
    ::= { cucsFabricPathEpEntry 5 }

cucsFabricPathEpEpDn OBJECT-TYPE
    SYNTAX       SnmpAdminString
    MAX-ACCESS   read-only
    STATUS       current
    DESCRIPTION
        "Cisco UCS fabric:PathEp:epDn managed object property"
    ::= { cucsFabricPathEpEntry 6 }

cucsFabricPathEpIfRole OBJECT-TYPE
    SYNTAX       CucsNetworkPortRole
    MAX-ACCESS   read-only
    STATUS       current
    DESCRIPTION
        "Cisco UCS fabric:PathEp:ifRole managed object property"
    ::= { cucsFabricPathEpEntry 7 }

cucsFabricPathEpIfType OBJECT-TYPE
    SYNTAX       CucsFabricPathEpIfType
    MAX-ACCESS   read-only
    STATUS       current
    DESCRIPTION
        "Cisco UCS fabric:PathEp:ifType managed object property"
    ::= { cucsFabricPathEpEntry 8 }

cucsFabricPathEpLocale OBJECT-TYPE
    SYNTAX       CucsFabricPathEpLocale
    MAX-ACCESS   read-only
    STATUS       current
    DESCRIPTION
        "Cisco UCS fabric:PathEp:locale managed object property"
    ::= { cucsFabricPathEpEntry 9 }

cucsFabricPathEpName OBJECT-TYPE
    SYNTAX       SnmpAdminString
    MAX-ACCESS   read-only
    STATUS       current
    DESCRIPTION
        "Cisco UCS fabric:PathEp:name managed object property"
    ::= { cucsFabricPathEpEntry 10 }

cucsFabricPathEpPeerDn OBJECT-TYPE
    SYNTAX       SnmpAdminString
    MAX-ACCESS   read-only
    STATUS       current
    DESCRIPTION
        "Cisco UCS fabric:PathEp:peerDn managed object property"
    ::= { cucsFabricPathEpEntry 11 }

cucsFabricPathEpPeerPortId OBJECT-TYPE
    SYNTAX       Gauge32
    MAX-ACCESS   read-only
    STATUS       current
    DESCRIPTION
        "Cisco UCS fabric:PathEp:peerPortId managed object property"
    ::= { cucsFabricPathEpEntry 12 }

cucsFabricPathEpPeerSlotId OBJECT-TYPE
    SYNTAX       Gauge32
    MAX-ACCESS   read-only
    STATUS       current
    DESCRIPTION
        "Cisco UCS fabric:PathEp:peerSlotId managed object property"
    ::= { cucsFabricPathEpEntry 13 }

cucsFabricPathEpPortId OBJECT-TYPE
    SYNTAX       Gauge32
    MAX-ACCESS   read-only
    STATUS       current
    DESCRIPTION
        "Cisco UCS fabric:PathEp:portId managed object property"
    ::= { cucsFabricPathEpEntry 14 }

cucsFabricPathEpSide OBJECT-TYPE
    SYNTAX       CucsNetworkSide
    MAX-ACCESS   read-only
    STATUS       current
    DESCRIPTION
        "Cisco UCS fabric:PathEp:side managed object property"
    ::= { cucsFabricPathEpEntry 15 }

cucsFabricPathEpSlotId OBJECT-TYPE
    SYNTAX       Gauge32
    MAX-ACCESS   read-only
    STATUS       current
    DESCRIPTION
        "Cisco UCS fabric:PathEp:slotId managed object property"
    ::= { cucsFabricPathEpEntry 16 }

cucsFabricPathEpSwitchId OBJECT-TYPE
    SYNTAX       CucsNetworkSwitchId
    MAX-ACCESS   read-only
    STATUS       current
    DESCRIPTION
        "Cisco UCS fabric:PathEp:switchId managed object property"
    ::= { cucsFabricPathEpEntry 17 }

cucsFabricPathEpTransport OBJECT-TYPE
    SYNTAX       CucsNetworkTransport
    MAX-ACCESS   read-only
    STATUS       current
    DESCRIPTION
        "Cisco UCS fabric:PathEp:transport managed object property"
    ::= { cucsFabricPathEpEntry 18 }

cucsFabricPathEpType OBJECT-TYPE
    SYNTAX       CucsNetworkConnectionType
    MAX-ACCESS   read-only
    STATUS       current
    DESCRIPTION
        "Cisco UCS fabric:PathEp:type managed object property"
    ::= { cucsFabricPathEpEntry 19 }

cucsFabricPathEpDiagLldpTransmit OBJECT-TYPE
    SYNTAX       TruthValue
    MAX-ACCESS   read-only
    STATUS       current
    DESCRIPTION
        "Cisco UCS fabric:PathEp:diagLldpTransmit managed object property"
    ::= { cucsFabricPathEpEntry 20 }

cucsFabricPathEpPeerChassisId OBJECT-TYPE
    SYNTAX       Gauge32
    MAX-ACCESS   read-only
    STATUS       current
    DESCRIPTION
        "Cisco UCS fabric:PathEp:peerChassisId managed object property"
    ::= { cucsFabricPathEpEntry 21 }

cucsFabricPathEpPeerMac OBJECT-TYPE
    SYNTAX       MacAddress
    MAX-ACCESS   read-only
    STATUS       current
    DESCRIPTION
        "Cisco UCS fabric:PathEp:peerMac managed object property"
    ::= { cucsFabricPathEpEntry 22 }

cucsFabricSanCloudTable OBJECT-TYPE
    SYNTAX           SEQUENCE OF CucsFabricSanCloudEntry
    MAX-ACCESS       not-accessible
    STATUS           current
    DESCRIPTION
        "Cisco UCS fabric:SanCloud managed object table"
    ::= { cucsFabricObjects 52 }

cucsFabricSanCloudEntry OBJECT-TYPE
    SYNTAX           CucsFabricSanCloudEntry
    MAX-ACCESS       not-accessible
    STATUS           current
    DESCRIPTION
        "Entry for the cucsFabricSanCloudTable table."
    INDEX { cucsFabricSanCloudInstanceId }
    ::= { cucsFabricSanCloudTable 1 }

CucsFabricSanCloudEntry ::= SEQUENCE {
    cucsFabricSanCloudInstanceId                                     CucsManagedObjectId,
    cucsFabricSanCloudDn                                             CucsManagedObjectDn,
    cucsFabricSanCloudRn                                             SnmpAdminString,
    cucsFabricSanCloudFsmDescr                                       SnmpAdminString,
    cucsFabricSanCloudFsmPrev                                        SnmpAdminString,
    cucsFabricSanCloudFsmProgr                                       Gauge32,
    cucsFabricSanCloudFsmRmtInvErrCode                               Gauge32,
    cucsFabricSanCloudFsmRmtInvErrDescr                              SnmpAdminString,
    cucsFabricSanCloudFsmRmtInvRslt                                  CucsConditionRemoteInvRslt,
    cucsFabricSanCloudFsmStageDescr                                  SnmpAdminString,
    cucsFabricSanCloudFsmStamp                                       DateAndTime,
    cucsFabricSanCloudFsmStatus                                      SnmpAdminString,
    cucsFabricSanCloudFsmTry                                         Gauge32,
    cucsFabricSanCloudMode                                           CucsFabricSwitchingMode
}

cucsFabricSanCloudInstanceId OBJECT-TYPE
    SYNTAX       CucsManagedObjectId
    MAX-ACCESS   not-accessible
    STATUS       current
    DESCRIPTION
        "Instance identifier of the managed object."
    ::= { cucsFabricSanCloudEntry 1 }

cucsFabricSanCloudDn OBJECT-TYPE
    SYNTAX       CucsManagedObjectDn
    MAX-ACCESS   read-only
    STATUS       current
    DESCRIPTION
        "Cisco UCS fabric:SanCloud:dn managed object property"
    ::= { cucsFabricSanCloudEntry 2 }

cucsFabricSanCloudRn OBJECT-TYPE
    SYNTAX       SnmpAdminString
    MAX-ACCESS   read-only
    STATUS       current
    DESCRIPTION
        "Cisco UCS fabric:SanCloud:rn managed object property"
    ::= { cucsFabricSanCloudEntry 3 }

cucsFabricSanCloudFsmDescr OBJECT-TYPE
    SYNTAX       SnmpAdminString
    MAX-ACCESS   read-only
    STATUS       current
    DESCRIPTION
        "Cisco UCS fabric:SanCloud:fsmDescr managed object property"
    ::= { cucsFabricSanCloudEntry 4 }

cucsFabricSanCloudFsmPrev OBJECT-TYPE
    SYNTAX       SnmpAdminString
    MAX-ACCESS   read-only
    STATUS       current
    DESCRIPTION
        "Cisco UCS fabric:SanCloud:fsmPrev managed object property"
    ::= { cucsFabricSanCloudEntry 5 }

cucsFabricSanCloudFsmProgr OBJECT-TYPE
    SYNTAX       Gauge32
    MAX-ACCESS   read-only
    STATUS       current
    DESCRIPTION
        "Cisco UCS fabric:SanCloud:fsmProgr managed object property"
    ::= { cucsFabricSanCloudEntry 6 }

cucsFabricSanCloudFsmRmtInvErrCode OBJECT-TYPE
    SYNTAX       Gauge32
    MAX-ACCESS   read-only
    STATUS       current
    DESCRIPTION
        "Cisco UCS fabric:SanCloud:fsmRmtInvErrCode managed
        object property"
    ::= { cucsFabricSanCloudEntry 7 }

cucsFabricSanCloudFsmRmtInvErrDescr OBJECT-TYPE
    SYNTAX       SnmpAdminString
    MAX-ACCESS   read-only
    STATUS       current
    DESCRIPTION
        "Cisco UCS fabric:SanCloud:fsmRmtInvErrDescr managed
        object property"
    ::= { cucsFabricSanCloudEntry 8 }

cucsFabricSanCloudFsmRmtInvRslt OBJECT-TYPE
    SYNTAX       CucsConditionRemoteInvRslt
    MAX-ACCESS   read-only
    STATUS       current
    DESCRIPTION
        "Cisco UCS fabric:SanCloud:fsmRmtInvRslt managed object property"
    ::= { cucsFabricSanCloudEntry 9 }

cucsFabricSanCloudFsmStageDescr OBJECT-TYPE
    SYNTAX       SnmpAdminString
    MAX-ACCESS   read-only
    STATUS       current
    DESCRIPTION
        "Cisco UCS fabric:SanCloud:fsmStageDescr managed object property"
    ::= { cucsFabricSanCloudEntry 10 }

cucsFabricSanCloudFsmStamp OBJECT-TYPE
    SYNTAX       DateAndTime
    MAX-ACCESS   read-only
    STATUS       current
    DESCRIPTION
        "Cisco UCS fabric:SanCloud:fsmStamp managed object property"
    ::= { cucsFabricSanCloudEntry 11 }

cucsFabricSanCloudFsmStatus OBJECT-TYPE
    SYNTAX       SnmpAdminString
    MAX-ACCESS   read-only
    STATUS       current
    DESCRIPTION
        "Cisco UCS fabric:SanCloud:fsmStatus managed object property"
    ::= { cucsFabricSanCloudEntry 12 }

cucsFabricSanCloudFsmTry OBJECT-TYPE
    SYNTAX       Gauge32
    MAX-ACCESS   read-only
    STATUS       current
    DESCRIPTION
        "Cisco UCS fabric:SanCloud:fsmTry managed object property"
    ::= { cucsFabricSanCloudEntry 13 }

cucsFabricSanCloudMode OBJECT-TYPE
    SYNTAX       CucsFabricSwitchingMode
    MAX-ACCESS   read-only
    STATUS       current
    DESCRIPTION
        "Cisco UCS fabric:SanCloud:mode managed object property"
    ::= { cucsFabricSanCloudEntry 14 }

cucsFabricSanCloudFsmTaskTable OBJECT-TYPE
    SYNTAX           SEQUENCE OF CucsFabricSanCloudFsmTaskEntry
    MAX-ACCESS       not-accessible
    STATUS           current
    DESCRIPTION
        "Cisco UCS fabric:SanCloudFsmTask managed object table"
    ::= { cucsFabricObjects 53 }

cucsFabricSanCloudFsmTaskEntry OBJECT-TYPE
    SYNTAX           CucsFabricSanCloudFsmTaskEntry
    MAX-ACCESS       not-accessible
    STATUS           current
    DESCRIPTION
        "Entry for the cucsFabricSanCloudFsmTaskTable table."
    INDEX { cucsFabricSanCloudFsmTaskInstanceId }
    ::= { cucsFabricSanCloudFsmTaskTable 1 }

CucsFabricSanCloudFsmTaskEntry ::= SEQUENCE {
    cucsFabricSanCloudFsmTaskInstanceId                              CucsManagedObjectId,
    cucsFabricSanCloudFsmTaskDn                                      CucsManagedObjectDn,
    cucsFabricSanCloudFsmTaskRn                                      SnmpAdminString,
    cucsFabricSanCloudFsmTaskCompletion                              CucsFsmCompletion,
    cucsFabricSanCloudFsmTaskFlags                                   CucsFsmFlags,
    cucsFabricSanCloudFsmTaskItem                                    CucsFabricSanCloudFsmTaskItem,
    cucsFabricSanCloudFsmTaskSeqId                                   Gauge32
}

cucsFabricSanCloudFsmTaskInstanceId OBJECT-TYPE
    SYNTAX       CucsManagedObjectId
    MAX-ACCESS   not-accessible
    STATUS       current
    DESCRIPTION
        "Instance identifier of the managed object."
    ::= { cucsFabricSanCloudFsmTaskEntry 1 }

cucsFabricSanCloudFsmTaskDn OBJECT-TYPE
    SYNTAX       CucsManagedObjectDn
    MAX-ACCESS   read-only
    STATUS       current
    DESCRIPTION
        "Cisco UCS fabric:SanCloudFsmTask:dn managed object property"
    ::= { cucsFabricSanCloudFsmTaskEntry 2 }

cucsFabricSanCloudFsmTaskRn OBJECT-TYPE
    SYNTAX       SnmpAdminString
    MAX-ACCESS   read-only
    STATUS       current
    DESCRIPTION
        "Cisco UCS fabric:SanCloudFsmTask:rn managed object property"
    ::= { cucsFabricSanCloudFsmTaskEntry 3 }

cucsFabricSanCloudFsmTaskCompletion OBJECT-TYPE
    SYNTAX       CucsFsmCompletion
    MAX-ACCESS   read-only
    STATUS       current
    DESCRIPTION
        "Cisco UCS fabric:SanCloudFsmTask:completion managed
        object property"
    ::= { cucsFabricSanCloudFsmTaskEntry 4 }

cucsFabricSanCloudFsmTaskFlags OBJECT-TYPE
    SYNTAX       CucsFsmFlags
    MAX-ACCESS   read-only
    STATUS       current
    DESCRIPTION
        "Cisco UCS fabric:SanCloudFsmTask:flags managed object property"
    ::= { cucsFabricSanCloudFsmTaskEntry 5 }

cucsFabricSanCloudFsmTaskItem OBJECT-TYPE
    SYNTAX       CucsFabricSanCloudFsmTaskItem
    MAX-ACCESS   read-only
    STATUS       current
    DESCRIPTION
        "Cisco UCS fabric:SanCloudFsmTask:item managed object property"
    ::= { cucsFabricSanCloudFsmTaskEntry 6 }

cucsFabricSanCloudFsmTaskSeqId OBJECT-TYPE
    SYNTAX       Gauge32
    MAX-ACCESS   read-only
    STATUS       current
    DESCRIPTION
        "Cisco UCS fabric:SanCloudFsmTask:seqId managed object property"
    ::= { cucsFabricSanCloudFsmTaskEntry 7 }

cucsFabricSanMonCloudTable OBJECT-TYPE
    SYNTAX           SEQUENCE OF CucsFabricSanMonCloudEntry
    MAX-ACCESS       not-accessible
    STATUS           current
    DESCRIPTION
        "Cisco UCS fabric:SanMonCloud managed object table"
    ::= { cucsFabricObjects 54 }

cucsFabricSanMonCloudEntry OBJECT-TYPE
    SYNTAX           CucsFabricSanMonCloudEntry
    MAX-ACCESS       not-accessible
    STATUS           current
    DESCRIPTION
        "Entry for the cucsFabricSanMonCloudTable table."
    INDEX { cucsFabricSanMonCloudInstanceId }
    ::= { cucsFabricSanMonCloudTable 1 }

CucsFabricSanMonCloudEntry ::= SEQUENCE {
    cucsFabricSanMonCloudInstanceId                                  CucsManagedObjectId,
    cucsFabricSanMonCloudDn                                          CucsManagedObjectDn,
    cucsFabricSanMonCloudRn                                          SnmpAdminString,
    cucsFabricSanMonCloudMode                                        CucsFabricSwitchingMode
}

cucsFabricSanMonCloudInstanceId OBJECT-TYPE
    SYNTAX       CucsManagedObjectId
    MAX-ACCESS   not-accessible
    STATUS       current
    DESCRIPTION
        "Instance identifier of the managed object."
    ::= { cucsFabricSanMonCloudEntry 1 }

cucsFabricSanMonCloudDn OBJECT-TYPE
    SYNTAX       CucsManagedObjectDn
    MAX-ACCESS   read-only
    STATUS       current
    DESCRIPTION
        "Cisco UCS fabric:SanMonCloud:dn managed object property"
    ::= { cucsFabricSanMonCloudEntry 2 }

cucsFabricSanMonCloudRn OBJECT-TYPE
    SYNTAX       SnmpAdminString
    MAX-ACCESS   read-only
    STATUS       current
    DESCRIPTION
        "Cisco UCS fabric:SanMonCloud:rn managed object property"
    ::= { cucsFabricSanMonCloudEntry 3 }

cucsFabricSanMonCloudMode OBJECT-TYPE
    SYNTAX       CucsFabricSwitchingMode
    MAX-ACCESS   read-only
    STATUS       current
    DESCRIPTION
        "Cisco UCS fabric:SanMonCloud:mode managed object property"
    ::= { cucsFabricSanMonCloudEntry 4 }

cucsFabricSanPinGroupTable OBJECT-TYPE
    SYNTAX           SEQUENCE OF CucsFabricSanPinGroupEntry
    MAX-ACCESS       not-accessible
    STATUS           current
    DESCRIPTION
        "Cisco UCS fabric:SanPinGroup managed object table"
    ::= { cucsFabricObjects 55 }

cucsFabricSanPinGroupEntry OBJECT-TYPE
    SYNTAX           CucsFabricSanPinGroupEntry
    MAX-ACCESS       not-accessible
    STATUS           current
    DESCRIPTION
        "Entry for the cucsFabricSanPinGroupTable table."
    INDEX { cucsFabricSanPinGroupInstanceId }
    ::= { cucsFabricSanPinGroupTable 1 }

CucsFabricSanPinGroupEntry ::= SEQUENCE {
    cucsFabricSanPinGroupInstanceId                                  CucsManagedObjectId,
    cucsFabricSanPinGroupDn                                          CucsManagedObjectDn,
    cucsFabricSanPinGroupRn                                          SnmpAdminString,
    cucsFabricSanPinGroupDescr                                       SnmpAdminString,
    cucsFabricSanPinGroupIntId                                       SnmpAdminString,
    cucsFabricSanPinGroupName                                        SnmpAdminString,
    cucsFabricSanPinGroupSize                                        Gauge32
}

cucsFabricSanPinGroupInstanceId OBJECT-TYPE
    SYNTAX       CucsManagedObjectId
    MAX-ACCESS   not-accessible
    STATUS       current
    DESCRIPTION
        "Instance identifier of the managed object."
    ::= { cucsFabricSanPinGroupEntry 1 }

cucsFabricSanPinGroupDn OBJECT-TYPE
    SYNTAX       CucsManagedObjectDn
    MAX-ACCESS   read-only
    STATUS       current
    DESCRIPTION
        "Cisco UCS fabric:SanPinGroup:dn managed object property"
    ::= { cucsFabricSanPinGroupEntry 2 }

cucsFabricSanPinGroupRn OBJECT-TYPE
    SYNTAX       SnmpAdminString
    MAX-ACCESS   read-only
    STATUS       current
    DESCRIPTION
        "Cisco UCS fabric:SanPinGroup:rn managed object property"
    ::= { cucsFabricSanPinGroupEntry 3 }

cucsFabricSanPinGroupDescr OBJECT-TYPE
    SYNTAX       SnmpAdminString
    MAX-ACCESS   read-only
    STATUS       current
    DESCRIPTION
        "Cisco UCS fabric:SanPinGroup:descr managed object property"
    ::= { cucsFabricSanPinGroupEntry 4 }

cucsFabricSanPinGroupIntId OBJECT-TYPE
    SYNTAX       SnmpAdminString
    MAX-ACCESS   read-only
    STATUS       current
    DESCRIPTION
        "Cisco UCS fabric:SanPinGroup:intId managed object property"
    ::= { cucsFabricSanPinGroupEntry 5 }

cucsFabricSanPinGroupName OBJECT-TYPE
    SYNTAX       SnmpAdminString
    MAX-ACCESS   read-only
    STATUS       current
    DESCRIPTION
        "Cisco UCS fabric:SanPinGroup:name managed object property"
    ::= { cucsFabricSanPinGroupEntry 6 }

cucsFabricSanPinGroupSize OBJECT-TYPE
    SYNTAX       Gauge32
    MAX-ACCESS   read-only
    STATUS       current
    DESCRIPTION
        "Cisco UCS fabric:SanPinGroup:size managed object property"
    ::= { cucsFabricSanPinGroupEntry 7 }

cucsFabricSanPinTargetTable OBJECT-TYPE
    SYNTAX           SEQUENCE OF CucsFabricSanPinTargetEntry
    MAX-ACCESS       not-accessible
    STATUS           current
    DESCRIPTION
        "Cisco UCS fabric:SanPinTarget managed object table"
    ::= { cucsFabricObjects 56 }

cucsFabricSanPinTargetEntry OBJECT-TYPE
    SYNTAX           CucsFabricSanPinTargetEntry
    MAX-ACCESS       not-accessible
    STATUS           current
    DESCRIPTION
        "Entry for the cucsFabricSanPinTargetTable table."
    INDEX { cucsFabricSanPinTargetInstanceId }
    ::= { cucsFabricSanPinTargetTable 1 }

CucsFabricSanPinTargetEntry ::= SEQUENCE {
    cucsFabricSanPinTargetInstanceId                                 CucsManagedObjectId,
    cucsFabricSanPinTargetDn                                         CucsManagedObjectDn,
    cucsFabricSanPinTargetRn                                         SnmpAdminString,
    cucsFabricSanPinTargetEpDn                                       SnmpAdminString,
    cucsFabricSanPinTargetFabricId                                   SnmpAdminString
}

cucsFabricSanPinTargetInstanceId OBJECT-TYPE
    SYNTAX       CucsManagedObjectId
    MAX-ACCESS   not-accessible
    STATUS       current
    DESCRIPTION
        "Instance identifier of the managed object."
    ::= { cucsFabricSanPinTargetEntry 1 }

cucsFabricSanPinTargetDn OBJECT-TYPE
    SYNTAX       CucsManagedObjectDn
    MAX-ACCESS   read-only
    STATUS       current
    DESCRIPTION
        "Cisco UCS fabric:SanPinTarget:dn managed object property"
    ::= { cucsFabricSanPinTargetEntry 2 }

cucsFabricSanPinTargetRn OBJECT-TYPE
    SYNTAX       SnmpAdminString
    MAX-ACCESS   read-only
    STATUS       current
    DESCRIPTION
        "Cisco UCS fabric:SanPinTarget:rn managed object property"
    ::= { cucsFabricSanPinTargetEntry 3 }

cucsFabricSanPinTargetEpDn OBJECT-TYPE
    SYNTAX       SnmpAdminString
    MAX-ACCESS   read-only
    STATUS       current
    DESCRIPTION
        "Cisco UCS fabric:SanPinTarget:epDn managed object property"
    ::= { cucsFabricSanPinTargetEntry 4 }

cucsFabricSanPinTargetFabricId OBJECT-TYPE
    SYNTAX       SnmpAdminString
    MAX-ACCESS   read-only
    STATUS       current
    DESCRIPTION
        "Cisco UCS fabric:SanPinTarget:fabricId managed object property"
    ::= { cucsFabricSanPinTargetEntry 5 }

cucsFabricSwChPhEpTable OBJECT-TYPE
    SYNTAX           SEQUENCE OF CucsFabricSwChPhEpEntry
    MAX-ACCESS       not-accessible
    STATUS           current
    DESCRIPTION
        "Cisco UCS fabric:SwChPhEp managed object table"
    ::= { cucsFabricObjects 57 }

cucsFabricSwChPhEpEntry OBJECT-TYPE
    SYNTAX           CucsFabricSwChPhEpEntry
    MAX-ACCESS       not-accessible
    STATUS           current
    DESCRIPTION
        "Entry for the cucsFabricSwChPhEpTable table."
    INDEX { cucsFabricSwChPhEpInstanceId }
    ::= { cucsFabricSwChPhEpTable 1 }

CucsFabricSwChPhEpEntry ::= SEQUENCE {
    cucsFabricSwChPhEpInstanceId                                     CucsManagedObjectId,
    cucsFabricSwChPhEpDn                                             CucsManagedObjectDn,
    cucsFabricSwChPhEpRn                                             SnmpAdminString,
    cucsFabricSwChPhEpAdminState                                     CucsFabricInternalEpAdminState,
    cucsFabricSwChPhEpChassisId                                      Gauge32,
    cucsFabricSwChPhEpEpDn                                           SnmpAdminString,
    cucsFabricSwChPhEpEqType                                         CucsEquipmentFabricEpType,
    cucsFabricSwChPhEpIfRole                                         CucsFabricSwChEpIfRole,
    cucsFabricSwChPhEpIfType                                         CucsFabricPIoEpIfType,
    cucsFabricSwChPhEpLc                                             CucsFabricLifeCycle,
    cucsFabricSwChPhEpLicGP                                          Unsigned64,
    cucsFabricSwChPhEpLicState                                       CucsLicenseState,
    cucsFabricSwChPhEpLocale                                         CucsFabricInternalEpLocale,
    cucsFabricSwChPhEpModel                                          SnmpAdminString,
    cucsFabricSwChPhEpName                                           SnmpAdminString,
    cucsFabricSwChPhEpPeerDn                                         SnmpAdminString,
    cucsFabricSwChPhEpPeerPortId                                     Gauge32,
    cucsFabricSwChPhEpPeerSlotId                                     Gauge32,
    cucsFabricSwChPhEpPortId                                         CucsFabricPIoEpPortId,
    cucsFabricSwChPhEpRevision                                       SnmpAdminString,
    cucsFabricSwChPhEpSerial                                         SnmpAdminString,
    cucsFabricSwChPhEpSlotId                                         CucsFabricPIoEpSlotId,
    cucsFabricSwChPhEpSwitchId                                       CucsNetworkSwitchId,
    cucsFabricSwChPhEpTransport                                      CucsNetworkTransport,
    cucsFabricSwChPhEpType                                           CucsFabricSwChEpType,
    cucsFabricSwChPhEpVendor                                         SnmpAdminString,
    cucsFabricSwChPhEpPeerChassisId                                  Gauge32,
    cucsFabricSwChPhEpFltAggr                                        Unsigned64
}

cucsFabricSwChPhEpInstanceId OBJECT-TYPE
    SYNTAX       CucsManagedObjectId
    MAX-ACCESS   not-accessible
    STATUS       current
    DESCRIPTION
        "Instance identifier of the managed object."
    ::= { cucsFabricSwChPhEpEntry 1 }

cucsFabricSwChPhEpDn OBJECT-TYPE
    SYNTAX       CucsManagedObjectDn
    MAX-ACCESS   read-only
    STATUS       current
    DESCRIPTION
        "Cisco UCS fabric:SwChPhEp:dn managed object property"
    ::= { cucsFabricSwChPhEpEntry 2 }

cucsFabricSwChPhEpRn OBJECT-TYPE
    SYNTAX       SnmpAdminString
    MAX-ACCESS   read-only
    STATUS       current
    DESCRIPTION
        "Cisco UCS fabric:SwChPhEp:rn managed object property"
    ::= { cucsFabricSwChPhEpEntry 3 }

cucsFabricSwChPhEpAdminState OBJECT-TYPE
    SYNTAX       CucsFabricInternalEpAdminState
    MAX-ACCESS   read-only
    STATUS       current
    DESCRIPTION
        "Cisco UCS fabric:SwChPhEp:adminState managed object property"
    ::= { cucsFabricSwChPhEpEntry 4 }

cucsFabricSwChPhEpChassisId OBJECT-TYPE
    SYNTAX       Gauge32
    MAX-ACCESS   read-only
    STATUS       current
    DESCRIPTION
        "Cisco UCS fabric:SwChPhEp:chassisId managed object property"
    ::= { cucsFabricSwChPhEpEntry 5 }

cucsFabricSwChPhEpEpDn OBJECT-TYPE
    SYNTAX       SnmpAdminString
    MAX-ACCESS   read-only
    STATUS       current
    DESCRIPTION
        "Cisco UCS fabric:SwChPhEp:epDn managed object property"
    ::= { cucsFabricSwChPhEpEntry 6 }

cucsFabricSwChPhEpEqType OBJECT-TYPE
    SYNTAX       CucsEquipmentFabricEpType
    MAX-ACCESS   read-only
    STATUS       current
    DESCRIPTION
        "Cisco UCS fabric:SwChPhEp:eqType managed object property"
    ::= { cucsFabricSwChPhEpEntry 7 }

cucsFabricSwChPhEpIfRole OBJECT-TYPE
    SYNTAX       CucsFabricSwChEpIfRole
    MAX-ACCESS   read-only
    STATUS       current
    DESCRIPTION
        "Cisco UCS fabric:SwChPhEp:ifRole managed object property"
    ::= { cucsFabricSwChPhEpEntry 8 }

cucsFabricSwChPhEpIfType OBJECT-TYPE
    SYNTAX       CucsFabricPIoEpIfType
    MAX-ACCESS   read-only
    STATUS       current
    DESCRIPTION
        "Cisco UCS fabric:SwChPhEp:ifType managed object property"
    ::= { cucsFabricSwChPhEpEntry 9 }

cucsFabricSwChPhEpLc OBJECT-TYPE
    SYNTAX       CucsFabricLifeCycle
    MAX-ACCESS   read-only
    STATUS       current
    DESCRIPTION
        "Cisco UCS fabric:SwChPhEp:lc managed object property"
    ::= { cucsFabricSwChPhEpEntry 10 }

cucsFabricSwChPhEpLicGP OBJECT-TYPE
    SYNTAX       Unsigned64
    MAX-ACCESS   read-only
    STATUS       current
    DESCRIPTION
        "Cisco UCS fabric:SwChPhEp:licGP managed object property"
    ::= { cucsFabricSwChPhEpEntry 11 }

cucsFabricSwChPhEpLicState OBJECT-TYPE
    SYNTAX       CucsLicenseState
    MAX-ACCESS   read-only
    STATUS       current
    DESCRIPTION
        "Cisco UCS fabric:SwChPhEp:licState managed object property"
    ::= { cucsFabricSwChPhEpEntry 12 }

cucsFabricSwChPhEpLocale OBJECT-TYPE
    SYNTAX       CucsFabricInternalEpLocale
    MAX-ACCESS   read-only
    STATUS       current
    DESCRIPTION
        "Cisco UCS fabric:SwChPhEp:locale managed object property"
    ::= { cucsFabricSwChPhEpEntry 13 }

cucsFabricSwChPhEpModel OBJECT-TYPE
    SYNTAX       SnmpAdminString
    MAX-ACCESS   read-only
    STATUS       current
    DESCRIPTION
        "Cisco UCS fabric:SwChPhEp:model managed object property"
    ::= { cucsFabricSwChPhEpEntry 14 }

cucsFabricSwChPhEpName OBJECT-TYPE
    SYNTAX       SnmpAdminString
    MAX-ACCESS   read-only
    STATUS       current
    DESCRIPTION
        "Cisco UCS fabric:SwChPhEp:name managed object property"
    ::= { cucsFabricSwChPhEpEntry 15 }

cucsFabricSwChPhEpPeerDn OBJECT-TYPE
    SYNTAX       SnmpAdminString
    MAX-ACCESS   read-only
    STATUS       current
    DESCRIPTION
        "Cisco UCS fabric:SwChPhEp:peerDn managed object property"
    ::= { cucsFabricSwChPhEpEntry 16 }

cucsFabricSwChPhEpPeerPortId OBJECT-TYPE
    SYNTAX       Gauge32
    MAX-ACCESS   read-only
    STATUS       current
    DESCRIPTION
        "Cisco UCS fabric:SwChPhEp:peerPortId managed object property"
    ::= { cucsFabricSwChPhEpEntry 17 }

cucsFabricSwChPhEpPeerSlotId OBJECT-TYPE
    SYNTAX       Gauge32
    MAX-ACCESS   read-only
    STATUS       current
    DESCRIPTION
        "Cisco UCS fabric:SwChPhEp:peerSlotId managed object property"
    ::= { cucsFabricSwChPhEpEntry 18 }

cucsFabricSwChPhEpPortId OBJECT-TYPE
    SYNTAX       CucsFabricPIoEpPortId
    MAX-ACCESS   read-only
    STATUS       current
    DESCRIPTION
        "Cisco UCS fabric:SwChPhEp:portId managed object property"
    ::= { cucsFabricSwChPhEpEntry 19 }

cucsFabricSwChPhEpRevision OBJECT-TYPE
    SYNTAX       SnmpAdminString
    MAX-ACCESS   read-only
    STATUS       current
    DESCRIPTION
        "Cisco UCS fabric:SwChPhEp:revision managed object property"
    ::= { cucsFabricSwChPhEpEntry 20 }

cucsFabricSwChPhEpSerial OBJECT-TYPE
    SYNTAX       SnmpAdminString
    MAX-ACCESS   read-only
    STATUS       current
    DESCRIPTION
        "Cisco UCS fabric:SwChPhEp:serial managed object property"
    ::= { cucsFabricSwChPhEpEntry 21 }

cucsFabricSwChPhEpSlotId OBJECT-TYPE
    SYNTAX       CucsFabricPIoEpSlotId
    MAX-ACCESS   read-only
    STATUS       current
    DESCRIPTION
        "Cisco UCS fabric:SwChPhEp:slotId managed object property"
    ::= { cucsFabricSwChPhEpEntry 22 }

cucsFabricSwChPhEpSwitchId OBJECT-TYPE
    SYNTAX       CucsNetworkSwitchId
    MAX-ACCESS   read-only
    STATUS       current
    DESCRIPTION
        "Cisco UCS fabric:SwChPhEp:switchId managed object property"
    ::= { cucsFabricSwChPhEpEntry 23 }

cucsFabricSwChPhEpTransport OBJECT-TYPE
    SYNTAX       CucsNetworkTransport
    MAX-ACCESS   read-only
    STATUS       current
    DESCRIPTION
        "Cisco UCS fabric:SwChPhEp:transport managed object property"
    ::= { cucsFabricSwChPhEpEntry 24 }

cucsFabricSwChPhEpType OBJECT-TYPE
    SYNTAX       CucsFabricSwChEpType
    MAX-ACCESS   read-only
    STATUS       current
    DESCRIPTION
        "Cisco UCS fabric:SwChPhEp:type managed object property"
    ::= { cucsFabricSwChPhEpEntry 25 }

cucsFabricSwChPhEpVendor OBJECT-TYPE
    SYNTAX       SnmpAdminString
    MAX-ACCESS   read-only
    STATUS       current
    DESCRIPTION
        "Cisco UCS fabric:SwChPhEp:vendor managed object property"
    ::= { cucsFabricSwChPhEpEntry 26 }

cucsFabricSwChPhEpPeerChassisId OBJECT-TYPE
    SYNTAX       Gauge32
    MAX-ACCESS   read-only
    STATUS       current
    DESCRIPTION
        "Cisco UCS fabric:SwChPhEp:peerChassisId managed object property"
    ::= { cucsFabricSwChPhEpEntry 27 }

cucsFabricSwChPhEpFltAggr OBJECT-TYPE
    SYNTAX       Unsigned64
    MAX-ACCESS   read-only
    STATUS       current
    DESCRIPTION
        "Cisco UCS fabric:SwChPhEp:fltAggr managed object property"
    ::= { cucsFabricSwChPhEpEntry 28 }

cucsFabricVConTable OBJECT-TYPE
    SYNTAX           SEQUENCE OF CucsFabricVConEntry
    MAX-ACCESS       not-accessible
    STATUS           current
    DESCRIPTION
        "Cisco UCS fabric:VCon managed object table"
    ::= { cucsFabricObjects 58 }

cucsFabricVConEntry OBJECT-TYPE
    SYNTAX           CucsFabricVConEntry
    MAX-ACCESS       not-accessible
    STATUS           current
    DESCRIPTION
        "Entry for the cucsFabricVConTable table."
    INDEX { cucsFabricVConInstanceId }
    ::= { cucsFabricVConTable 1 }

CucsFabricVConEntry ::= SEQUENCE {
    cucsFabricVConInstanceId                                         CucsManagedObjectId,
    cucsFabricVConDn                                                 CucsManagedObjectDn,
    cucsFabricVConRn                                                 SnmpAdminString,
    cucsFabricVConFabric                                             SnmpAdminString,
    cucsFabricVConId                                                 SnmpAdminString,
    cucsFabricVConPlacement                                          CucsFabricVConPlacementPref,
    cucsFabricVConSelect                                             CucsFabricVConSelectPref,
    cucsFabricVConShare                                              CucsFabricVConSharePref,
    cucsFabricVConTransport                                          CucsFabricVConTransportPref
}

cucsFabricVConInstanceId OBJECT-TYPE
    SYNTAX       CucsManagedObjectId
    MAX-ACCESS   not-accessible
    STATUS       current
    DESCRIPTION
        "Instance identifier of the managed object."
    ::= { cucsFabricVConEntry 1 }

cucsFabricVConDn OBJECT-TYPE
    SYNTAX       CucsManagedObjectDn
    MAX-ACCESS   read-only
    STATUS       current
    DESCRIPTION
        "Cisco UCS fabric:VCon:dn managed object property"
    ::= { cucsFabricVConEntry 2 }

cucsFabricVConRn OBJECT-TYPE
    SYNTAX       SnmpAdminString
    MAX-ACCESS   read-only
    STATUS       current
    DESCRIPTION
        "Cisco UCS fabric:VCon:rn managed object property"
    ::= { cucsFabricVConEntry 3 }

cucsFabricVConFabric OBJECT-TYPE
    SYNTAX       SnmpAdminString
    MAX-ACCESS   read-only
    STATUS       current
    DESCRIPTION
        "Cisco UCS fabric:VCon:fabric managed object property"
    ::= { cucsFabricVConEntry 4 }

cucsFabricVConId OBJECT-TYPE
    SYNTAX       SnmpAdminString
    MAX-ACCESS   read-only
    STATUS       current
    DESCRIPTION
        "Cisco UCS fabric:VCon:id managed object property"
    ::= { cucsFabricVConEntry 5 }

cucsFabricVConPlacement OBJECT-TYPE
    SYNTAX       CucsFabricVConPlacementPref
    MAX-ACCESS   read-only
    STATUS       current
    DESCRIPTION
        "Cisco UCS fabric:VCon:placement managed object property"
    ::= { cucsFabricVConEntry 6 }

cucsFabricVConSelect OBJECT-TYPE
    SYNTAX       CucsFabricVConSelectPref
    MAX-ACCESS   read-only
    STATUS       current
    DESCRIPTION
        "Cisco UCS fabric:VCon:select managed object property"
    ::= { cucsFabricVConEntry 7 }

cucsFabricVConShare OBJECT-TYPE
    SYNTAX       CucsFabricVConSharePref
    MAX-ACCESS   read-only
    STATUS       current
    DESCRIPTION
        "Cisco UCS fabric:VCon:share managed object property"
    ::= { cucsFabricVConEntry 8 }

cucsFabricVConTransport OBJECT-TYPE
    SYNTAX       CucsFabricVConTransportPref
    MAX-ACCESS   read-only
    STATUS       current
    DESCRIPTION
        "Cisco UCS fabric:VCon:transport managed object property"
    ::= { cucsFabricVConEntry 9 }

cucsFabricVConProfileTable OBJECT-TYPE
    SYNTAX           SEQUENCE OF CucsFabricVConProfileEntry
    MAX-ACCESS       not-accessible
    STATUS           current
    DESCRIPTION
        "Cisco UCS fabric:VConProfile managed object table"
    ::= { cucsFabricObjects 59 }

cucsFabricVConProfileEntry OBJECT-TYPE
    SYNTAX           CucsFabricVConProfileEntry
    MAX-ACCESS       not-accessible
    STATUS           current
    DESCRIPTION
        "Entry for the cucsFabricVConProfileTable table."
    INDEX { cucsFabricVConProfileInstanceId }
    ::= { cucsFabricVConProfileTable 1 }

CucsFabricVConProfileEntry ::= SEQUENCE {
    cucsFabricVConProfileInstanceId                                  CucsManagedObjectId,
    cucsFabricVConProfileDn                                          CucsManagedObjectDn,
    cucsFabricVConProfileRn                                          SnmpAdminString,
    cucsFabricVConProfileDescr                                       SnmpAdminString,
    cucsFabricVConProfileIntId                                       SnmpAdminString,
    cucsFabricVConProfileName                                        SnmpAdminString
}

cucsFabricVConProfileInstanceId OBJECT-TYPE
    SYNTAX       CucsManagedObjectId
    MAX-ACCESS   not-accessible
    STATUS       current
    DESCRIPTION
        "Instance identifier of the managed object."
    ::= { cucsFabricVConProfileEntry 1 }

cucsFabricVConProfileDn OBJECT-TYPE
    SYNTAX       CucsManagedObjectDn
    MAX-ACCESS   read-only
    STATUS       current
    DESCRIPTION
        "Cisco UCS fabric:VConProfile:dn managed object property"
    ::= { cucsFabricVConProfileEntry 2 }

cucsFabricVConProfileRn OBJECT-TYPE
    SYNTAX       SnmpAdminString
    MAX-ACCESS   read-only
    STATUS       current
    DESCRIPTION
        "Cisco UCS fabric:VConProfile:rn managed object property"
    ::= { cucsFabricVConProfileEntry 3 }

cucsFabricVConProfileDescr OBJECT-TYPE
    SYNTAX       SnmpAdminString
    MAX-ACCESS   read-only
    STATUS       current
    DESCRIPTION
        "Cisco UCS fabric:VConProfile:descr managed object property"
    ::= { cucsFabricVConProfileEntry 4 }

cucsFabricVConProfileIntId OBJECT-TYPE
    SYNTAX       SnmpAdminString
    MAX-ACCESS   read-only
    STATUS       current
    DESCRIPTION
        "Cisco UCS fabric:VConProfile:intId managed object property"
    ::= { cucsFabricVConProfileEntry 5 }

cucsFabricVConProfileName OBJECT-TYPE
    SYNTAX       SnmpAdminString
    MAX-ACCESS   read-only
    STATUS       current
    DESCRIPTION
        "Cisco UCS fabric:VConProfile:name managed object property"
    ::= { cucsFabricVConProfileEntry 6 }

cucsFabricVlanTable OBJECT-TYPE
    SYNTAX           SEQUENCE OF CucsFabricVlanEntry
    MAX-ACCESS       not-accessible
    STATUS           current
    DESCRIPTION
        "Cisco UCS fabric:Vlan managed object table"
    ::= { cucsFabricObjects 60 }

cucsFabricVlanEntry OBJECT-TYPE
    SYNTAX           CucsFabricVlanEntry
    MAX-ACCESS       not-accessible
    STATUS           current
    DESCRIPTION
        "Entry for the cucsFabricVlanTable table."
    INDEX { cucsFabricVlanInstanceId }
    ::= { cucsFabricVlanTable 1 }

CucsFabricVlanEntry ::= SEQUENCE {
    cucsFabricVlanInstanceId                                         CucsManagedObjectId,
    cucsFabricVlanDn                                                 CucsManagedObjectDn,
    cucsFabricVlanRn                                                 SnmpAdminString,
    cucsFabricVlanDefaultNet                                         TruthValue,
    cucsFabricVlanEndPtDn                                            SnmpAdminString,
    cucsFabricVlanId                                                 Gauge32,
    cucsFabricVlanIfRole                                             CucsFabricVnetEpIfRole,
    cucsFabricVlanIfType                                             CucsNetworkVnetEpIfType,
    cucsFabricVlanLocale                                             CucsFabricVnetEpLocale,
    cucsFabricVlanName                                               SnmpAdminString,
    cucsFabricVlanPeerDn                                             SnmpAdminString,
    cucsFabricVlanPubNwDn                                            SnmpAdminString,
    cucsFabricVlanPubNwId                                            Gauge32,
    cucsFabricVlanPubNwName                                          SnmpAdminString,
    cucsFabricVlanSharing                                            CucsFabricAVlanSharing,
    cucsFabricVlanSwitchId                                           CucsFabricVlanSwitchId,
    cucsFabricVlanTransport                                          CucsFabricAVlanTransport,
    cucsFabricVlanType                                               CucsFabricAVlanType,
    cucsFabricVlanOperState                                          CucsFabricVlanOperState
}

cucsFabricVlanInstanceId OBJECT-TYPE
    SYNTAX       CucsManagedObjectId
    MAX-ACCESS   not-accessible
    STATUS       current
    DESCRIPTION
        "Instance identifier of the managed object."
    ::= { cucsFabricVlanEntry 1 }

cucsFabricVlanDn OBJECT-TYPE
    SYNTAX       CucsManagedObjectDn
    MAX-ACCESS   read-only
    STATUS       current
    DESCRIPTION
        "Cisco UCS fabric:Vlan:dn managed object property"
    ::= { cucsFabricVlanEntry 2 }

cucsFabricVlanRn OBJECT-TYPE
    SYNTAX       SnmpAdminString
    MAX-ACCESS   read-only
    STATUS       current
    DESCRIPTION
        "Cisco UCS fabric:Vlan:rn managed object property"
    ::= { cucsFabricVlanEntry 3 }

cucsFabricVlanDefaultNet OBJECT-TYPE
    SYNTAX       TruthValue
    MAX-ACCESS   read-only
    STATUS       current
    DESCRIPTION
        "Cisco UCS fabric:Vlan:defaultNet managed object property"
    ::= { cucsFabricVlanEntry 4 }

cucsFabricVlanEndPtDn OBJECT-TYPE
    SYNTAX       SnmpAdminString
    MAX-ACCESS   read-only
    STATUS       current
    DESCRIPTION
        "Cisco UCS fabric:Vlan:epDn managed object property"
    ::= { cucsFabricVlanEntry 5 }

cucsFabricVlanId OBJECT-TYPE
    SYNTAX       Gauge32
    MAX-ACCESS   read-only
    STATUS       current
    DESCRIPTION
        "Cisco UCS fabric:Vlan:id managed object property"
    ::= { cucsFabricVlanEntry 6 }

cucsFabricVlanIfRole OBJECT-TYPE
    SYNTAX       CucsFabricVnetEpIfRole
    MAX-ACCESS   read-only
    STATUS       current
    DESCRIPTION
        "Cisco UCS fabric:Vlan:ifRole managed object property"
    ::= { cucsFabricVlanEntry 7 }

cucsFabricVlanIfType OBJECT-TYPE
    SYNTAX       CucsNetworkVnetEpIfType
    MAX-ACCESS   read-only
    STATUS       current
    DESCRIPTION
        "Cisco UCS fabric:Vlan:ifType managed object property"
    ::= { cucsFabricVlanEntry 8 }

cucsFabricVlanLocale OBJECT-TYPE
    SYNTAX       CucsFabricVnetEpLocale
    MAX-ACCESS   read-only
    STATUS       current
    DESCRIPTION
        "Cisco UCS fabric:Vlan:locale managed object property"
    ::= { cucsFabricVlanEntry 9 }

cucsFabricVlanName OBJECT-TYPE
    SYNTAX       SnmpAdminString
    MAX-ACCESS   read-only
    STATUS       current
    DESCRIPTION
        "Cisco UCS fabric:Vlan:name managed object property"
    ::= { cucsFabricVlanEntry 10 }

cucsFabricVlanPeerDn OBJECT-TYPE
    SYNTAX       SnmpAdminString
    MAX-ACCESS   read-only
    STATUS       current
    DESCRIPTION
        "Cisco UCS fabric:Vlan:peerDn managed object property"
    ::= { cucsFabricVlanEntry 11 }

cucsFabricVlanPubNwDn OBJECT-TYPE
    SYNTAX       SnmpAdminString
    MAX-ACCESS   read-only
    STATUS       current
    DESCRIPTION
        "Cisco UCS fabric:Vlan:pubNwDn managed object property"
    ::= { cucsFabricVlanEntry 12 }

cucsFabricVlanPubNwId OBJECT-TYPE
    SYNTAX       Gauge32
    MAX-ACCESS   read-only
    STATUS       current
    DESCRIPTION
        "Cisco UCS fabric:Vlan:pubNwId managed object property"
    ::= { cucsFabricVlanEntry 13 }

cucsFabricVlanPubNwName OBJECT-TYPE
    SYNTAX       SnmpAdminString
    MAX-ACCESS   read-only
    STATUS       current
    DESCRIPTION
        "Cisco UCS fabric:Vlan:pubNwName managed object property"
    ::= { cucsFabricVlanEntry 14 }

cucsFabricVlanSharing OBJECT-TYPE
    SYNTAX       CucsFabricAVlanSharing
    MAX-ACCESS   read-only
    STATUS       current
    DESCRIPTION
        "Cisco UCS fabric:Vlan:sharing managed object property"
    ::= { cucsFabricVlanEntry 15 }

cucsFabricVlanSwitchId OBJECT-TYPE
    SYNTAX       CucsFabricVlanSwitchId
    MAX-ACCESS   read-only
    STATUS       current
    DESCRIPTION
        "Cisco UCS fabric:Vlan:switchId managed object property"
    ::= { cucsFabricVlanEntry 16 }

cucsFabricVlanTransport OBJECT-TYPE
    SYNTAX       CucsFabricAVlanTransport
    MAX-ACCESS   read-only
    STATUS       current
    DESCRIPTION
        "Cisco UCS fabric:Vlan:transport managed object property"
    ::= { cucsFabricVlanEntry 17 }

cucsFabricVlanType OBJECT-TYPE
    SYNTAX       CucsFabricAVlanType
    MAX-ACCESS   read-only
    STATUS       current
    DESCRIPTION
        "Cisco UCS fabric:Vlan:type managed object property"
    ::= { cucsFabricVlanEntry 18 }

cucsFabricVlanOperState OBJECT-TYPE
    SYNTAX       CucsFabricVlanOperState
    MAX-ACCESS   read-only
    STATUS       current
    DESCRIPTION
        "Cisco UCS fabric:Vlan:operState managed object property"
    ::= { cucsFabricVlanEntry 19 }

cucsFabricVlanEpTable OBJECT-TYPE
    SYNTAX           SEQUENCE OF CucsFabricVlanEpEntry
    MAX-ACCESS       not-accessible
    STATUS           current
    DESCRIPTION
        "Cisco UCS fabric:VlanEp managed object table"
    ::= { cucsFabricObjects 61 }

cucsFabricVlanEpEntry OBJECT-TYPE
    SYNTAX           CucsFabricVlanEpEntry
    MAX-ACCESS       not-accessible
    STATUS           current
    DESCRIPTION
        "Entry for the cucsFabricVlanEpTable table."
    INDEX { cucsFabricVlanEpInstanceId }
    ::= { cucsFabricVlanEpTable 1 }

CucsFabricVlanEpEntry ::= SEQUENCE {
    cucsFabricVlanEpInstanceId                                       CucsManagedObjectId,
    cucsFabricVlanEpDn                                               CucsManagedObjectDn,
    cucsFabricVlanEpRn                                               SnmpAdminString,
    cucsFabricVlanEpEpDn                                             SnmpAdminString,
    cucsFabricVlanEpId                                               Gauge32,
    cucsFabricVlanEpIfRole                                           CucsFabricVnetEpIfRole,
    cucsFabricVlanEpIfType                                           CucsNetworkVnetEpIfType,
    cucsFabricVlanEpIsNative                                         TruthValue,
    cucsFabricVlanEpLocale                                           CucsFabricVnetEpLocale,
    cucsFabricVlanEpName                                             SnmpAdminString,
    cucsFabricVlanEpPeerDn                                           SnmpAdminString,
    cucsFabricVlanEpPubNwDn                                          SnmpAdminString,
    cucsFabricVlanEpPubNwId                                          Gauge32,
    cucsFabricVlanEpPubNwName                                        SnmpAdminString,
    cucsFabricVlanEpSharing                                          CucsFabricAVlanSharing,
    cucsFabricVlanEpSwitchId                                         CucsNetworkSwitchId,
    cucsFabricVlanEpTransport                                        CucsFabricAVlanTransport,
    cucsFabricVlanEpType                                             CucsFabricAVlanType,
    cucsFabricVlanEpOperState                                        CucsFabricVlanOperState
}

cucsFabricVlanEpInstanceId OBJECT-TYPE
    SYNTAX       CucsManagedObjectId
    MAX-ACCESS   not-accessible
    STATUS       current
    DESCRIPTION
        "Instance identifier of the managed object."
    ::= { cucsFabricVlanEpEntry 1 }

cucsFabricVlanEpDn OBJECT-TYPE
    SYNTAX       CucsManagedObjectDn
    MAX-ACCESS   read-only
    STATUS       current
    DESCRIPTION
        "Cisco UCS fabric:VlanEp:dn managed object property"
    ::= { cucsFabricVlanEpEntry 2 }

cucsFabricVlanEpRn OBJECT-TYPE
    SYNTAX       SnmpAdminString
    MAX-ACCESS   read-only
    STATUS       current
    DESCRIPTION
        "Cisco UCS fabric:VlanEp:rn managed object property"
    ::= { cucsFabricVlanEpEntry 3 }

cucsFabricVlanEpEpDn OBJECT-TYPE
    SYNTAX       SnmpAdminString
    MAX-ACCESS   read-only
    STATUS       current
    DESCRIPTION
        "Cisco UCS fabric:VlanEp:epDn managed object property"
    ::= { cucsFabricVlanEpEntry 4 }

cucsFabricVlanEpId OBJECT-TYPE
    SYNTAX       Gauge32
    MAX-ACCESS   read-only
    STATUS       current
    DESCRIPTION
        "Cisco UCS fabric:VlanEp:id managed object property"
    ::= { cucsFabricVlanEpEntry 5 }

cucsFabricVlanEpIfRole OBJECT-TYPE
    SYNTAX       CucsFabricVnetEpIfRole
    MAX-ACCESS   read-only
    STATUS       current
    DESCRIPTION
        "Cisco UCS fabric:VlanEp:ifRole managed object property"
    ::= { cucsFabricVlanEpEntry 6 }

cucsFabricVlanEpIfType OBJECT-TYPE
    SYNTAX       CucsNetworkVnetEpIfType
    MAX-ACCESS   read-only
    STATUS       current
    DESCRIPTION
        "Cisco UCS fabric:VlanEp:ifType managed object property"
    ::= { cucsFabricVlanEpEntry 7 }

cucsFabricVlanEpIsNative OBJECT-TYPE
    SYNTAX       TruthValue
    MAX-ACCESS   read-only
    STATUS       current
    DESCRIPTION
        "Cisco UCS fabric:VlanEp:isNative managed object property"
    ::= { cucsFabricVlanEpEntry 8 }

cucsFabricVlanEpLocale OBJECT-TYPE
    SYNTAX       CucsFabricVnetEpLocale
    MAX-ACCESS   read-only
    STATUS       current
    DESCRIPTION
        "Cisco UCS fabric:VlanEp:locale managed object property"
    ::= { cucsFabricVlanEpEntry 9 }

cucsFabricVlanEpName OBJECT-TYPE
    SYNTAX       SnmpAdminString
    MAX-ACCESS   read-only
    STATUS       current
    DESCRIPTION
        "Cisco UCS fabric:VlanEp:name managed object property"
    ::= { cucsFabricVlanEpEntry 10 }

cucsFabricVlanEpPeerDn OBJECT-TYPE
    SYNTAX       SnmpAdminString
    MAX-ACCESS   read-only
    STATUS       current
    DESCRIPTION
        "Cisco UCS fabric:VlanEp:peerDn managed object property"
    ::= { cucsFabricVlanEpEntry 11 }

cucsFabricVlanEpPubNwDn OBJECT-TYPE
    SYNTAX       SnmpAdminString
    MAX-ACCESS   read-only
    STATUS       current
    DESCRIPTION
        "Cisco UCS fabric:VlanEp:pubNwDn managed object property"
    ::= { cucsFabricVlanEpEntry 12 }

cucsFabricVlanEpPubNwId OBJECT-TYPE
    SYNTAX       Gauge32
    MAX-ACCESS   read-only
    STATUS       current
    DESCRIPTION
        "Cisco UCS fabric:VlanEp:pubNwId managed object property"
    ::= { cucsFabricVlanEpEntry 13 }

cucsFabricVlanEpPubNwName OBJECT-TYPE
    SYNTAX       SnmpAdminString
    MAX-ACCESS   read-only
    STATUS       current
    DESCRIPTION
        "Cisco UCS fabric:VlanEp:pubNwName managed object property"
    ::= { cucsFabricVlanEpEntry 14 }

cucsFabricVlanEpSharing OBJECT-TYPE
    SYNTAX       CucsFabricAVlanSharing
    MAX-ACCESS   read-only
    STATUS       current
    DESCRIPTION
        "Cisco UCS fabric:VlanEp:sharing managed object property"
    ::= { cucsFabricVlanEpEntry 15 }

cucsFabricVlanEpSwitchId OBJECT-TYPE
    SYNTAX       CucsNetworkSwitchId
    MAX-ACCESS   read-only
    STATUS       current
    DESCRIPTION
        "Cisco UCS fabric:VlanEp:switchId managed object property"
    ::= { cucsFabricVlanEpEntry 16 }

cucsFabricVlanEpTransport OBJECT-TYPE
    SYNTAX       CucsFabricAVlanTransport
    MAX-ACCESS   read-only
    STATUS       current
    DESCRIPTION
        "Cisco UCS fabric:VlanEp:transport managed object property"
    ::= { cucsFabricVlanEpEntry 17 }

cucsFabricVlanEpType OBJECT-TYPE
    SYNTAX       CucsFabricAVlanType
    MAX-ACCESS   read-only
    STATUS       current
    DESCRIPTION
        "Cisco UCS fabric:VlanEp:type managed object property"
    ::= { cucsFabricVlanEpEntry 18 }

cucsFabricVlanEpOperState OBJECT-TYPE
    SYNTAX       CucsFabricVlanOperState
    MAX-ACCESS   read-only
    STATUS       current
    DESCRIPTION
        "Cisco UCS fabric:VlanEp:operState managed object property"
    ::= { cucsFabricVlanEpEntry 19 }

cucsFabricVsanTable OBJECT-TYPE
    SYNTAX           SEQUENCE OF CucsFabricVsanEntry
    MAX-ACCESS       not-accessible
    STATUS           current
    DESCRIPTION
        "Cisco UCS fabric:Vsan managed object table"
    ::= { cucsFabricObjects 62 }

cucsFabricVsanEntry OBJECT-TYPE
    SYNTAX           CucsFabricVsanEntry
    MAX-ACCESS       not-accessible
    STATUS           current
    DESCRIPTION
        "Entry for the cucsFabricVsanTable table."
    INDEX { cucsFabricVsanInstanceId }
    ::= { cucsFabricVsanTable 1 }

CucsFabricVsanEntry ::= SEQUENCE {
    cucsFabricVsanInstanceId                                         CucsManagedObjectId,
    cucsFabricVsanDn                                                 CucsManagedObjectDn,
    cucsFabricVsanRn                                                 SnmpAdminString,
    cucsFabricVsanEndPtDn                                            SnmpAdminString,
    cucsFabricVsanFcoeVlan                                           Gauge32,
    cucsFabricVsanId                                                 Gauge32,
    cucsFabricVsanIfRole                                             CucsFabricVnetEpIfRole,
    cucsFabricVsanIfType                                             CucsNetworkVnetEpIfType,
    cucsFabricVsanLocale                                             CucsFabricVnetEpLocale,
    cucsFabricVsanName                                               SnmpAdminString,
    cucsFabricVsanPeerDn                                             SnmpAdminString,
    cucsFabricVsanSwitchId                                           CucsFabricVsanSwitchId,
    cucsFabricVsanTransport                                          CucsFabricAVsanTransport,
    cucsFabricVsanType                                               CucsFabricAVsanType,
    cucsFabricVsanDefaultZoning                                      CucsFabricDefaultZoningState,
    cucsFabricVsanFltAggr                                            Unsigned64,
    cucsFabricVsanOperState                                          CucsFabricVsanOperState
}

cucsFabricVsanInstanceId OBJECT-TYPE
    SYNTAX       CucsManagedObjectId
    MAX-ACCESS   not-accessible
    STATUS       current
    DESCRIPTION
        "Instance identifier of the managed object."
    ::= { cucsFabricVsanEntry 1 }

cucsFabricVsanDn OBJECT-TYPE
    SYNTAX       CucsManagedObjectDn
    MAX-ACCESS   read-only
    STATUS       current
    DESCRIPTION
        "Cisco UCS fabric:Vsan:dn managed object property"
    ::= { cucsFabricVsanEntry 2 }

cucsFabricVsanRn OBJECT-TYPE
    SYNTAX       SnmpAdminString
    MAX-ACCESS   read-only
    STATUS       current
    DESCRIPTION
        "Cisco UCS fabric:Vsan:rn managed object property"
    ::= { cucsFabricVsanEntry 3 }

cucsFabricVsanEndPtDn OBJECT-TYPE
    SYNTAX       SnmpAdminString
    MAX-ACCESS   read-only
    STATUS       current
    DESCRIPTION
        "Cisco UCS fabric:Vsan:epDn managed object property"
    ::= { cucsFabricVsanEntry 4 }

cucsFabricVsanFcoeVlan OBJECT-TYPE
    SYNTAX       Gauge32
    MAX-ACCESS   read-only
    STATUS       current
    DESCRIPTION
        "Cisco UCS fabric:Vsan:fcoeVlan managed object property"
    ::= { cucsFabricVsanEntry 5 }

cucsFabricVsanId OBJECT-TYPE
    SYNTAX       Gauge32
    MAX-ACCESS   read-only
    STATUS       current
    DESCRIPTION
        "Cisco UCS fabric:Vsan:id managed object property"
    ::= { cucsFabricVsanEntry 6 }

cucsFabricVsanIfRole OBJECT-TYPE
    SYNTAX       CucsFabricVnetEpIfRole
    MAX-ACCESS   read-only
    STATUS       current
    DESCRIPTION
        "Cisco UCS fabric:Vsan:ifRole managed object property"
    ::= { cucsFabricVsanEntry 7 }

cucsFabricVsanIfType OBJECT-TYPE
    SYNTAX       CucsNetworkVnetEpIfType
    MAX-ACCESS   read-only
    STATUS       current
    DESCRIPTION
        "Cisco UCS fabric:Vsan:ifType managed object property"
    ::= { cucsFabricVsanEntry 8 }

cucsFabricVsanLocale OBJECT-TYPE
    SYNTAX       CucsFabricVnetEpLocale
    MAX-ACCESS   read-only
    STATUS       current
    DESCRIPTION
        "Cisco UCS fabric:Vsan:locale managed object property"
    ::= { cucsFabricVsanEntry 9 }

cucsFabricVsanName OBJECT-TYPE
    SYNTAX       SnmpAdminString
    MAX-ACCESS   read-only
    STATUS       current
    DESCRIPTION
        "Cisco UCS fabric:Vsan:name managed object property"
    ::= { cucsFabricVsanEntry 10 }

cucsFabricVsanPeerDn OBJECT-TYPE
    SYNTAX       SnmpAdminString
    MAX-ACCESS   read-only
    STATUS       current
    DESCRIPTION
        "Cisco UCS fabric:Vsan:peerDn managed object property"
    ::= { cucsFabricVsanEntry 11 }

cucsFabricVsanSwitchId OBJECT-TYPE
    SYNTAX       CucsFabricVsanSwitchId
    MAX-ACCESS   read-only
    STATUS       current
    DESCRIPTION
        "Cisco UCS fabric:Vsan:switchId managed object property"
    ::= { cucsFabricVsanEntry 12 }

cucsFabricVsanTransport OBJECT-TYPE
    SYNTAX       CucsFabricAVsanTransport
    MAX-ACCESS   read-only
    STATUS       current
    DESCRIPTION
        "Cisco UCS fabric:Vsan:transport managed object property"
    ::= { cucsFabricVsanEntry 13 }

cucsFabricVsanType OBJECT-TYPE
    SYNTAX       CucsFabricAVsanType
    MAX-ACCESS   read-only
    STATUS       current
    DESCRIPTION
        "Cisco UCS fabric:Vsan:type managed object property"
    ::= { cucsFabricVsanEntry 14 }

cucsFabricVsanDefaultZoning OBJECT-TYPE
    SYNTAX       CucsFabricDefaultZoningState
    MAX-ACCESS   read-only
    STATUS       current
    DESCRIPTION
        "Cisco UCS fabric:Vsan:defaultZoning managed object property"
    ::= { cucsFabricVsanEntry 15 }

cucsFabricVsanFltAggr OBJECT-TYPE
    SYNTAX       Unsigned64
    MAX-ACCESS   read-only
    STATUS       current
    DESCRIPTION
        "Cisco UCS fabric:Vsan:fltAggr managed object property"
    ::= { cucsFabricVsanEntry 16 }

cucsFabricVsanOperState OBJECT-TYPE
    SYNTAX       CucsFabricVsanOperState
    MAX-ACCESS   read-only
    STATUS       current
    DESCRIPTION
        "Cisco UCS fabric:Vsan:operState managed object property"
    ::= { cucsFabricVsanEntry 17 }

cucsFabricVsanEpTable OBJECT-TYPE
    SYNTAX           SEQUENCE OF CucsFabricVsanEpEntry
    MAX-ACCESS       not-accessible
    STATUS           current
    DESCRIPTION
        "Cisco UCS fabric:VsanEp managed object table"
    ::= { cucsFabricObjects 63 }

cucsFabricVsanEpEntry OBJECT-TYPE
    SYNTAX           CucsFabricVsanEpEntry
    MAX-ACCESS       not-accessible
    STATUS           current
    DESCRIPTION
        "Entry for the cucsFabricVsanEpTable table."
    INDEX { cucsFabricVsanEpInstanceId }
    ::= { cucsFabricVsanEpTable 1 }

CucsFabricVsanEpEntry ::= SEQUENCE {
    cucsFabricVsanEpInstanceId                                       CucsManagedObjectId,
    cucsFabricVsanEpDn                                               CucsManagedObjectDn,
    cucsFabricVsanEpRn                                               SnmpAdminString,
    cucsFabricVsanEpEpDn                                             SnmpAdminString,
    cucsFabricVsanEpFcoeVlan                                         Gauge32,
    cucsFabricVsanEpId                                               Gauge32,
    cucsFabricVsanEpIfRole                                           CucsFabricVnetEpIfRole,
    cucsFabricVsanEpIfType                                           CucsNetworkVnetEpIfType,
    cucsFabricVsanEpLocale                                           CucsFabricVnetEpLocale,
    cucsFabricVsanEpName                                             SnmpAdminString,
    cucsFabricVsanEpPeerDn                                           SnmpAdminString,
    cucsFabricVsanEpSwitchId                                         CucsNetworkSwitchId,
    cucsFabricVsanEpTransport                                        CucsFabricAVsanTransport,
    cucsFabricVsanEpType                                             CucsFabricAVsanType,
    cucsFabricVsanEpOperState                                        CucsFabricVsanOperState
}

cucsFabricVsanEpInstanceId OBJECT-TYPE
    SYNTAX       CucsManagedObjectId
    MAX-ACCESS   not-accessible
    STATUS       current
    DESCRIPTION
        "Instance identifier of the managed object."
    ::= { cucsFabricVsanEpEntry 1 }

cucsFabricVsanEpDn OBJECT-TYPE
    SYNTAX       CucsManagedObjectDn
    MAX-ACCESS   read-only
    STATUS       current
    DESCRIPTION
        "Cisco UCS fabric:VsanEp:dn managed object property"
    ::= { cucsFabricVsanEpEntry 2 }

cucsFabricVsanEpRn OBJECT-TYPE
    SYNTAX       SnmpAdminString
    MAX-ACCESS   read-only
    STATUS       current
    DESCRIPTION
        "Cisco UCS fabric:VsanEp:rn managed object property"
    ::= { cucsFabricVsanEpEntry 3 }

cucsFabricVsanEpEpDn OBJECT-TYPE
    SYNTAX       SnmpAdminString
    MAX-ACCESS   read-only
    STATUS       current
    DESCRIPTION
        "Cisco UCS fabric:VsanEp:epDn managed object property"
    ::= { cucsFabricVsanEpEntry 4 }

cucsFabricVsanEpFcoeVlan OBJECT-TYPE
    SYNTAX       Gauge32
    MAX-ACCESS   read-only
    STATUS       current
    DESCRIPTION
        "Cisco UCS fabric:VsanEp:fcoeVlan managed object property"
    ::= { cucsFabricVsanEpEntry 5 }

cucsFabricVsanEpId OBJECT-TYPE
    SYNTAX       Gauge32
    MAX-ACCESS   read-only
    STATUS       current
    DESCRIPTION
        "Cisco UCS fabric:VsanEp:id managed object property"
    ::= { cucsFabricVsanEpEntry 6 }

cucsFabricVsanEpIfRole OBJECT-TYPE
    SYNTAX       CucsFabricVnetEpIfRole
    MAX-ACCESS   read-only
    STATUS       current
    DESCRIPTION
        "Cisco UCS fabric:VsanEp:ifRole managed object property"
    ::= { cucsFabricVsanEpEntry 7 }

cucsFabricVsanEpIfType OBJECT-TYPE
    SYNTAX       CucsNetworkVnetEpIfType
    MAX-ACCESS   read-only
    STATUS       current
    DESCRIPTION
        "Cisco UCS fabric:VsanEp:ifType managed object property"
    ::= { cucsFabricVsanEpEntry 8 }

cucsFabricVsanEpLocale OBJECT-TYPE
    SYNTAX       CucsFabricVnetEpLocale
    MAX-ACCESS   read-only
    STATUS       current
    DESCRIPTION
        "Cisco UCS fabric:VsanEp:locale managed object property"
    ::= { cucsFabricVsanEpEntry 9 }

cucsFabricVsanEpName OBJECT-TYPE
    SYNTAX       SnmpAdminString
    MAX-ACCESS   read-only
    STATUS       current
    DESCRIPTION
        "Cisco UCS fabric:VsanEp:name managed object property"
    ::= { cucsFabricVsanEpEntry 10 }

cucsFabricVsanEpPeerDn OBJECT-TYPE
    SYNTAX       SnmpAdminString
    MAX-ACCESS   read-only
    STATUS       current
    DESCRIPTION
        "Cisco UCS fabric:VsanEp:peerDn managed object property"
    ::= { cucsFabricVsanEpEntry 11 }

cucsFabricVsanEpSwitchId OBJECT-TYPE
    SYNTAX       CucsNetworkSwitchId
    MAX-ACCESS   read-only
    STATUS       current
    DESCRIPTION
        "Cisco UCS fabric:VsanEp:switchId managed object property"
    ::= { cucsFabricVsanEpEntry 12 }

cucsFabricVsanEpTransport OBJECT-TYPE
    SYNTAX       CucsFabricAVsanTransport
    MAX-ACCESS   read-only
    STATUS       current
    DESCRIPTION
        "Cisco UCS fabric:VsanEp:transport managed object property"
    ::= { cucsFabricVsanEpEntry 13 }

cucsFabricVsanEpType OBJECT-TYPE
    SYNTAX       CucsFabricAVsanType
    MAX-ACCESS   read-only
    STATUS       current
    DESCRIPTION
        "Cisco UCS fabric:VsanEp:type managed object property"
    ::= { cucsFabricVsanEpEntry 14 }

cucsFabricVsanEpOperState OBJECT-TYPE
    SYNTAX       CucsFabricVsanOperState
    MAX-ACCESS   read-only
    STATUS       current
    DESCRIPTION
        "Cisco UCS fabric:VsanEp:operState managed object property"
    ::= { cucsFabricVsanEpEntry 15 }

END
