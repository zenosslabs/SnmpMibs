-- *********************************************************************
-- CISCO-UNIFIED-COMPUTING-SW-MIB.my
-- 
-- MIB representation of the Cisco Unified Computing System
-- SW management information model package
-- 
-- Created September 2011 by Charles Bullis
-- 
-- Copyright (c) 2005-2011 Cisco Systems, Inc. All rights reserved.
-- 
-- *********************************************************************

CISCO-UNIFIED-COMPUTING-SW-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsConditionRemoteInvRslt,
    CucsDpsecForgedTransmit,
    CucsFabricAVlanSharing,
    CucsFabricAVlanTransport,
    CucsFabricAVlanType,
    CucsFabricAVsanTransport,
    CucsFabricAVsanType,
    CucsFabricAdminState,
    CucsFabricDefaultZoningState,
    CucsFabricEpVlanVlanType,
    CucsFabricEthEstcPortMode,
    CucsFabricEthPcProtocol,
    CucsFabricExternalEpAdminState,
    CucsFabricExternalEpLocale,
    CucsFabricPIoEpIfType,
    CucsFabricPIoEpPortId,
    CucsFabricPIoEpSlotId,
    CucsFabricTrafficDirection,
    CucsFabricVlanOperState,
    CucsFabricVnetEpIfRole,
    CucsFabricVnetEpLocale,
    CucsFabricVsanOperState,
    CucsFlowctrlFlowControl,
    CucsFlowctrlPriorityPause,
    CucsFsmCompletion,
    CucsFsmFlags,
    CucsFsmLifecycle,
    CucsLicenseState,
    CucsNetworkConnectionType,
    CucsNetworkLocale,
    CucsNetworkPortRole,
    CucsNetworkSwitchId,
    CucsNetworkTransport,
    CucsNetworkVnetEpIfType,
    CucsNwctrlAdminState,
    CucsNwctrlLinkFailAction,
    CucsPortEthSpeed,
    CucsPortSpeed,
    CucsSwAccessDomainFsmTaskItem,
    CucsSwAccessDomainLocale,
    CucsSwAccessDomainType,
    CucsSwAccessEpLocale,
    CucsSwAccessEpTransport,
    CucsSwBorderDomainLocale,
    CucsSwBorderEpLocale,
    CucsSwBorderPcLocale,
    CucsSwCIoEpIfType,
    CucsSwConfMode,
    CucsSwEnvStatsHistThresholded,
    CucsSwEnvStatsThresholded,
    CucsSwEstcEpLocale,
    CucsSwEthEstcEpTransport,
    CucsSwEthEstcPcTransport,
    CucsSwEthLanBorderFsmTaskItem,
    CucsSwEthLanBorderTransport,
    CucsSwEthLanEpTransport,
    CucsSwEthLanMonTransport,
    CucsSwEthLanPcTransport,
    CucsSwEthMonDestEpTransport,
    CucsSwEthMonFsmTaskItem,
    CucsSwEthMonSrcEpTransport,
    CucsSwEthMonTransport,
    CucsSwEthMonType,
    CucsSwEthTargetEpTransport,
    CucsSwFcEstcEpTransport,
    CucsSwFcMonDestEpTransport,
    CucsSwFcMonFsmTaskItem,
    CucsSwFcMonSrcEpTransport,
    CucsSwFcMonTransport,
    CucsSwFcMonType,
    CucsSwFcSanBorderFsmTaskItem,
    CucsSwFcSanBorderTransport,
    CucsSwFcSanBorderUplinkTrunking,
    CucsSwFcSanEpTransport,
    CucsSwFcSanMonTransport,
    CucsSwFcSanPcTransport,
    CucsSwFcoeEstcEpTransport,
    CucsSwLanBorderType,
    CucsSwLanEpIfRole,
    CucsSwLanEpType,
    CucsSwLanMonType,
    CucsSwLanPcIfRole,
    CucsSwLanPcType,
    CucsSwMonAdminState,
    CucsSwMonDomainLocale,
    CucsSwMonLifeCycle,
    CucsSwMonSrcEpLocale,
    CucsSwPIoEpIfType,
    CucsSwPIoEpLc,
    CucsSwPhysFsmTaskItem,
    CucsSwSanBorderType,
    CucsSwSanEpIfRole,
    CucsSwSanEpType,
    CucsSwSanMonType,
    CucsSwSanPcIfRole,
    CucsSwSanPcType,
    CucsSwSystemStatsHistThresholded,
    CucsSwSystemStatsThresholded,
    CucsSwTargetEpType,
    CucsSwUlanPurpose,
    CucsSwUtilityDomainFsmTaskItem,
    CucsSwUtilityDomainLocale,
    CucsSwUtilityDomainType,
    CucsSwVlanLc,
    CucsSwVlanPortNsAllocStatus
        FROM CISCO-UNIFIED-COMPUTING-TC-MIB;

cucsSwObjects MODULE-IDENTITY
    LAST-UPDATED    "201109150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        SW management information model package"
    ::= { ciscoUnifiedComputingMIBObjects 46 }

cucsSwAccessDomainTable OBJECT-TYPE
    SYNTAX           SEQUENCE OF CucsSwAccessDomainEntry
    MAX-ACCESS       not-accessible
    STATUS           current
    DESCRIPTION
        "Cisco UCS sw:AccessDomain managed object table"
    ::= { cucsSwObjects 1 }

cucsSwAccessDomainEntry OBJECT-TYPE
    SYNTAX           CucsSwAccessDomainEntry
    MAX-ACCESS       not-accessible
    STATUS           current
    DESCRIPTION
        "Entry for the cucsSwAccessDomainTable table."
    INDEX { cucsSwAccessDomainInstanceId }
    ::= { cucsSwAccessDomainTable 1 }

CucsSwAccessDomainEntry ::= SEQUENCE {
    cucsSwAccessDomainInstanceId                                     CucsManagedObjectId,
    cucsSwAccessDomainDn                                             CucsManagedObjectDn,
    cucsSwAccessDomainRn                                             SnmpAdminString,
    cucsSwAccessDomainFsmDescr                                       SnmpAdminString,
    cucsSwAccessDomainFsmPrev                                        SnmpAdminString,
    cucsSwAccessDomainFsmProgr                                       Gauge32,
    cucsSwAccessDomainFsmRmtInvErrCode                               Gauge32,
    cucsSwAccessDomainFsmRmtInvErrDescr                              SnmpAdminString,
    cucsSwAccessDomainFsmRmtInvRslt                                  CucsConditionRemoteInvRslt,
    cucsSwAccessDomainFsmStageDescr                                  SnmpAdminString,
    cucsSwAccessDomainFsmStamp                                       DateAndTime,
    cucsSwAccessDomainFsmStatus                                      SnmpAdminString,
    cucsSwAccessDomainFsmTry                                         Gauge32,
    cucsSwAccessDomainLocale                                         CucsSwAccessDomainLocale,
    cucsSwAccessDomainName                                           SnmpAdminString,
    cucsSwAccessDomainSwitchId                                       CucsNetworkSwitchId,
    cucsSwAccessDomainTransport                                      CucsNetworkTransport,
    cucsSwAccessDomainType                                           CucsSwAccessDomainType
}

cucsSwAccessDomainInstanceId OBJECT-TYPE
    SYNTAX       CucsManagedObjectId
    MAX-ACCESS   not-accessible
    STATUS       current
    DESCRIPTION
        "Instance identifier of the managed object."
    ::= { cucsSwAccessDomainEntry 1 }

cucsSwAccessDomainDn OBJECT-TYPE
    SYNTAX       CucsManagedObjectDn
    MAX-ACCESS   read-only
    STATUS       current
    DESCRIPTION
        "Cisco UCS sw:AccessDomain:dn managed object property"
    ::= { cucsSwAccessDomainEntry 2 }

cucsSwAccessDomainRn OBJECT-TYPE
    SYNTAX       SnmpAdminString
    MAX-ACCESS   read-only
    STATUS       current
    DESCRIPTION
        "Cisco UCS sw:AccessDomain:rn managed object property"
    ::= { cucsSwAccessDomainEntry 3 }

cucsSwAccessDomainFsmDescr OBJECT-TYPE
    SYNTAX       SnmpAdminString
    MAX-ACCESS   read-only
    STATUS       current
    DESCRIPTION
        "Cisco UCS sw:AccessDomain:fsmDescr managed object property"
    ::= { cucsSwAccessDomainEntry 4 }

cucsSwAccessDomainFsmPrev OBJECT-TYPE
    SYNTAX       SnmpAdminString
    MAX-ACCESS   read-only
    STATUS       current
    DESCRIPTION
        "Cisco UCS sw:AccessDomain:fsmPrev managed object property"
    ::= { cucsSwAccessDomainEntry 5 }

cucsSwAccessDomainFsmProgr OBJECT-TYPE
    SYNTAX       Gauge32
    MAX-ACCESS   read-only
    STATUS       current
    DESCRIPTION
        "Cisco UCS sw:AccessDomain:fsmProgr managed object property"
    ::= { cucsSwAccessDomainEntry 6 }

cucsSwAccessDomainFsmRmtInvErrCode OBJECT-TYPE
    SYNTAX       Gauge32
    MAX-ACCESS   read-only
    STATUS       current
    DESCRIPTION
        "Cisco UCS sw:AccessDomain:fsmRmtInvErrCode managed
        object property"
    ::= { cucsSwAccessDomainEntry 7 }

cucsSwAccessDomainFsmRmtInvErrDescr OBJECT-TYPE
    SYNTAX       SnmpAdminString
    MAX-ACCESS   read-only
    STATUS       current
    DESCRIPTION
        "Cisco UCS sw:AccessDomain:fsmRmtInvErrDescr managed
        object property"
    ::= { cucsSwAccessDomainEntry 8 }

cucsSwAccessDomainFsmRmtInvRslt OBJECT-TYPE
    SYNTAX       CucsConditionRemoteInvRslt
    MAX-ACCESS   read-only
    STATUS       current
    DESCRIPTION
        "Cisco UCS sw:AccessDomain:fsmRmtInvRslt managed object property"
    ::= { cucsSwAccessDomainEntry 9 }

cucsSwAccessDomainFsmStageDescr OBJECT-TYPE
    SYNTAX       SnmpAdminString
    MAX-ACCESS   read-only
    STATUS       current
    DESCRIPTION
        "Cisco UCS sw:AccessDomain:fsmStageDescr managed object property"
    ::= { cucsSwAccessDomainEntry 10 }

cucsSwAccessDomainFsmStamp OBJECT-TYPE
    SYNTAX       DateAndTime
    MAX-ACCESS   read-only
    STATUS       current
    DESCRIPTION
        "Cisco UCS sw:AccessDomain:fsmStamp managed object property"
    ::= { cucsSwAccessDomainEntry 11 }

cucsSwAccessDomainFsmStatus OBJECT-TYPE
    SYNTAX       SnmpAdminString
    MAX-ACCESS   read-only
    STATUS       current
    DESCRIPTION
        "Cisco UCS sw:AccessDomain:fsmStatus managed object property"
    ::= { cucsSwAccessDomainEntry 12 }

cucsSwAccessDomainFsmTry OBJECT-TYPE
    SYNTAX       Gauge32
    MAX-ACCESS   read-only
    STATUS       current
    DESCRIPTION
        "Cisco UCS sw:AccessDomain:fsmTry managed object property"
    ::= { cucsSwAccessDomainEntry 13 }

cucsSwAccessDomainLocale OBJECT-TYPE
    SYNTAX       CucsSwAccessDomainLocale
    MAX-ACCESS   read-only
    STATUS       current
    DESCRIPTION
        "Cisco UCS sw:AccessDomain:locale managed object property"
    ::= { cucsSwAccessDomainEntry 14 }

cucsSwAccessDomainName OBJECT-TYPE
    SYNTAX       SnmpAdminString
    MAX-ACCESS   read-only
    STATUS       current
    DESCRIPTION
        "Cisco UCS sw:AccessDomain:name managed object property"
    ::= { cucsSwAccessDomainEntry 15 }

cucsSwAccessDomainSwitchId OBJECT-TYPE
    SYNTAX       CucsNetworkSwitchId
    MAX-ACCESS   read-only
    STATUS       current
    DESCRIPTION
        "Cisco UCS sw:AccessDomain:switchId managed object property"
    ::= { cucsSwAccessDomainEntry 16 }

cucsSwAccessDomainTransport OBJECT-TYPE
    SYNTAX       CucsNetworkTransport
    MAX-ACCESS   read-only
    STATUS       current
    DESCRIPTION
        "Cisco UCS sw:AccessDomain:transport managed object property"
    ::= { cucsSwAccessDomainEntry 17 }

cucsSwAccessDomainType OBJECT-TYPE
    SYNTAX       CucsSwAccessDomainType
    MAX-ACCESS   read-only
    STATUS       current
    DESCRIPTION
        "Cisco UCS sw:AccessDomain:type managed object property"
    ::= { cucsSwAccessDomainEntry 18 }

cucsSwAccessDomainFsmTaskTable OBJECT-TYPE
    SYNTAX           SEQUENCE OF CucsSwAccessDomainFsmTaskEntry
    MAX-ACCESS       not-accessible
    STATUS           current
    DESCRIPTION
        "Cisco UCS sw:AccessDomainFsmTask managed object table"
    ::= { cucsSwObjects 2 }

cucsSwAccessDomainFsmTaskEntry OBJECT-TYPE
    SYNTAX           CucsSwAccessDomainFsmTaskEntry
    MAX-ACCESS       not-accessible
    STATUS           current
    DESCRIPTION
        "Entry for the cucsSwAccessDomainFsmTaskTable table."
    INDEX { cucsSwAccessDomainFsmTaskInstanceId }
    ::= { cucsSwAccessDomainFsmTaskTable 1 }

CucsSwAccessDomainFsmTaskEntry ::= SEQUENCE {
    cucsSwAccessDomainFsmTaskInstanceId                              CucsManagedObjectId,
    cucsSwAccessDomainFsmTaskDn                                      CucsManagedObjectDn,
    cucsSwAccessDomainFsmTaskRn                                      SnmpAdminString,
    cucsSwAccessDomainFsmTaskCompletion                              CucsFsmCompletion,
    cucsSwAccessDomainFsmTaskFlags                                   CucsFsmFlags,
    cucsSwAccessDomainFsmTaskItem                                    CucsSwAccessDomainFsmTaskItem,
    cucsSwAccessDomainFsmTaskSeqId                                   Gauge32
}

cucsSwAccessDomainFsmTaskInstanceId OBJECT-TYPE
    SYNTAX       CucsManagedObjectId
    MAX-ACCESS   not-accessible
    STATUS       current
    DESCRIPTION
        "Instance identifier of the managed object."
    ::= { cucsSwAccessDomainFsmTaskEntry 1 }

cucsSwAccessDomainFsmTaskDn OBJECT-TYPE
    SYNTAX       CucsManagedObjectDn
    MAX-ACCESS   read-only
    STATUS       current
    DESCRIPTION
        "Cisco UCS sw:AccessDomainFsmTask:dn managed object property"
    ::= { cucsSwAccessDomainFsmTaskEntry 2 }

cucsSwAccessDomainFsmTaskRn OBJECT-TYPE
    SYNTAX       SnmpAdminString
    MAX-ACCESS   read-only
    STATUS       current
    DESCRIPTION
        "Cisco UCS sw:AccessDomainFsmTask:rn managed object property"
    ::= { cucsSwAccessDomainFsmTaskEntry 3 }

cucsSwAccessDomainFsmTaskCompletion OBJECT-TYPE
    SYNTAX       CucsFsmCompletion
    MAX-ACCESS   read-only
    STATUS       current
    DESCRIPTION
        "Cisco UCS sw:AccessDomainFsmTask:completion managed
        object property"
    ::= { cucsSwAccessDomainFsmTaskEntry 4 }

cucsSwAccessDomainFsmTaskFlags OBJECT-TYPE
    SYNTAX       CucsFsmFlags
    MAX-ACCESS   read-only
    STATUS       current
    DESCRIPTION
        "Cisco UCS sw:AccessDomainFsmTask:flags managed object property"
    ::= { cucsSwAccessDomainFsmTaskEntry 5 }

cucsSwAccessDomainFsmTaskItem OBJECT-TYPE
    SYNTAX       CucsSwAccessDomainFsmTaskItem
    MAX-ACCESS   read-only
    STATUS       current
    DESCRIPTION
        "Cisco UCS sw:AccessDomainFsmTask:item managed object property"
    ::= { cucsSwAccessDomainFsmTaskEntry 6 }

cucsSwAccessDomainFsmTaskSeqId OBJECT-TYPE
    SYNTAX       Gauge32
    MAX-ACCESS   read-only
    STATUS       current
    DESCRIPTION
        "Cisco UCS sw:AccessDomainFsmTask:seqId managed object property"
    ::= { cucsSwAccessDomainFsmTaskEntry 7 }

cucsSwAccessEpTable OBJECT-TYPE
    SYNTAX           SEQUENCE OF CucsSwAccessEpEntry
    MAX-ACCESS       not-accessible
    STATUS           current
    DESCRIPTION
        "Cisco UCS sw:AccessEp managed object table"
    ::= { cucsSwObjects 3 }

cucsSwAccessEpEntry OBJECT-TYPE
    SYNTAX           CucsSwAccessEpEntry
    MAX-ACCESS       not-accessible
    STATUS           current
    DESCRIPTION
        "Entry for the cucsSwAccessEpTable table."
    INDEX { cucsSwAccessEpInstanceId }
    ::= { cucsSwAccessEpTable 1 }

CucsSwAccessEpEntry ::= SEQUENCE {
    cucsSwAccessEpInstanceId                                         CucsManagedObjectId,
    cucsSwAccessEpDn                                                 CucsManagedObjectDn,
    cucsSwAccessEpRn                                                 SnmpAdminString,
    cucsSwAccessEpAdminState                                         CucsFabricAdminState,
    cucsSwAccessEpChassisId                                          Gauge32,
    cucsSwAccessEpEpDn                                               SnmpAdminString,
    cucsSwAccessEpIfRole                                             CucsNetworkPortRole,
    cucsSwAccessEpIfType                                             CucsSwPIoEpIfType,
    cucsSwAccessEpLocale                                             CucsSwAccessEpLocale,
    cucsSwAccessEpName                                               SnmpAdminString,
    cucsSwAccessEpPeerDn                                             SnmpAdminString,
    cucsSwAccessEpPeerPortId                                         Gauge32,
    cucsSwAccessEpPeerSlotId                                         Gauge32,
    cucsSwAccessEpPortId                                             Gauge32,
    cucsSwAccessEpSlotId                                             Gauge32,
    cucsSwAccessEpSwitchId                                           CucsNetworkSwitchId,
    cucsSwAccessEpTransport                                          CucsSwAccessEpTransport,
    cucsSwAccessEpType                                               CucsNetworkConnectionType,
    cucsSwAccessEpEncap                                              Gauge32,
    cucsSwAccessEpNsSize                                             Gauge32,
    cucsSwAccessEpPeerChassisId                                      Gauge32,
    cucsSwAccessEpLc                                                 CucsSwPIoEpLc
}

cucsSwAccessEpInstanceId OBJECT-TYPE
    SYNTAX       CucsManagedObjectId
    MAX-ACCESS   not-accessible
    STATUS       current
    DESCRIPTION
        "Instance identifier of the managed object."
    ::= { cucsSwAccessEpEntry 1 }

cucsSwAccessEpDn OBJECT-TYPE
    SYNTAX       CucsManagedObjectDn
    MAX-ACCESS   read-only
    STATUS       current
    DESCRIPTION
        "Cisco UCS sw:AccessEp:dn managed object property"
    ::= { cucsSwAccessEpEntry 2 }

cucsSwAccessEpRn OBJECT-TYPE
    SYNTAX       SnmpAdminString
    MAX-ACCESS   read-only
    STATUS       current
    DESCRIPTION
        "Cisco UCS sw:AccessEp:rn managed object property"
    ::= { cucsSwAccessEpEntry 3 }

cucsSwAccessEpAdminState OBJECT-TYPE
    SYNTAX       CucsFabricAdminState
    MAX-ACCESS   read-only
    STATUS       current
    DESCRIPTION
        "Cisco UCS sw:AccessEp:adminState managed object property"
    ::= { cucsSwAccessEpEntry 4 }

cucsSwAccessEpChassisId OBJECT-TYPE
    SYNTAX       Gauge32
    MAX-ACCESS   read-only
    STATUS       current
    DESCRIPTION
        "Cisco UCS sw:AccessEp:chassisId managed object property"
    ::= { cucsSwAccessEpEntry 5 }

cucsSwAccessEpEpDn OBJECT-TYPE
    SYNTAX       SnmpAdminString
    MAX-ACCESS   read-only
    STATUS       current
    DESCRIPTION
        "Cisco UCS sw:AccessEp:epDn managed object property"
    ::= { cucsSwAccessEpEntry 6 }

cucsSwAccessEpIfRole OBJECT-TYPE
    SYNTAX       CucsNetworkPortRole
    MAX-ACCESS   read-only
    STATUS       current
    DESCRIPTION
        "Cisco UCS sw:AccessEp:ifRole managed object property"
    ::= { cucsSwAccessEpEntry 7 }

cucsSwAccessEpIfType OBJECT-TYPE
    SYNTAX       CucsSwPIoEpIfType
    MAX-ACCESS   read-only
    STATUS       current
    DESCRIPTION
        "Cisco UCS sw:AccessEp:ifType managed object property"
    ::= { cucsSwAccessEpEntry 8 }

cucsSwAccessEpLocale OBJECT-TYPE
    SYNTAX       CucsSwAccessEpLocale
    MAX-ACCESS   read-only
    STATUS       current
    DESCRIPTION
        "Cisco UCS sw:AccessEp:locale managed object property"
    ::= { cucsSwAccessEpEntry 9 }

cucsSwAccessEpName OBJECT-TYPE
    SYNTAX       SnmpAdminString
    MAX-ACCESS   read-only
    STATUS       current
    DESCRIPTION
        "Cisco UCS sw:AccessEp:name managed object property"
    ::= { cucsSwAccessEpEntry 10 }

cucsSwAccessEpPeerDn OBJECT-TYPE
    SYNTAX       SnmpAdminString
    MAX-ACCESS   read-only
    STATUS       current
    DESCRIPTION
        "Cisco UCS sw:AccessEp:peerDn managed object property"
    ::= { cucsSwAccessEpEntry 11 }

cucsSwAccessEpPeerPortId OBJECT-TYPE
    SYNTAX       Gauge32
    MAX-ACCESS   read-only
    STATUS       current
    DESCRIPTION
        "Cisco UCS sw:AccessEp:peerPortId managed object property"
    ::= { cucsSwAccessEpEntry 12 }

cucsSwAccessEpPeerSlotId OBJECT-TYPE
    SYNTAX       Gauge32
    MAX-ACCESS   read-only
    STATUS       current
    DESCRIPTION
        "Cisco UCS sw:AccessEp:peerSlotId managed object property"
    ::= { cucsSwAccessEpEntry 13 }

cucsSwAccessEpPortId OBJECT-TYPE
    SYNTAX       Gauge32
    MAX-ACCESS   read-only
    STATUS       current
    DESCRIPTION
        "Cisco UCS sw:AccessEp:portId managed object property"
    ::= { cucsSwAccessEpEntry 14 }

cucsSwAccessEpSlotId OBJECT-TYPE
    SYNTAX       Gauge32
    MAX-ACCESS   read-only
    STATUS       current
    DESCRIPTION
        "Cisco UCS sw:AccessEp:slotId managed object property"
    ::= { cucsSwAccessEpEntry 15 }

cucsSwAccessEpSwitchId OBJECT-TYPE
    SYNTAX       CucsNetworkSwitchId
    MAX-ACCESS   read-only
    STATUS       current
    DESCRIPTION
        "Cisco UCS sw:AccessEp:switchId managed object property"
    ::= { cucsSwAccessEpEntry 16 }

cucsSwAccessEpTransport OBJECT-TYPE
    SYNTAX       CucsSwAccessEpTransport
    MAX-ACCESS   read-only
    STATUS       current
    DESCRIPTION
        "Cisco UCS sw:AccessEp:transport managed object property"
    ::= { cucsSwAccessEpEntry 17 }

cucsSwAccessEpType OBJECT-TYPE
    SYNTAX       CucsNetworkConnectionType
    MAX-ACCESS   read-only
    STATUS       current
    DESCRIPTION
        "Cisco UCS sw:AccessEp:type managed object property"
    ::= { cucsSwAccessEpEntry 18 }

cucsSwAccessEpEncap OBJECT-TYPE
    SYNTAX       Gauge32
    MAX-ACCESS   read-only
    STATUS       current
    DESCRIPTION
        "Cisco UCS sw:AccessEp:encap managed object property"
    ::= { cucsSwAccessEpEntry 19 }

cucsSwAccessEpNsSize OBJECT-TYPE
    SYNTAX       Gauge32
    MAX-ACCESS   read-only
    STATUS       current
    DESCRIPTION
        "Cisco UCS sw:AccessEp:nsSize managed object property"
    ::= { cucsSwAccessEpEntry 20 }

cucsSwAccessEpPeerChassisId OBJECT-TYPE
    SYNTAX       Gauge32
    MAX-ACCESS   read-only
    STATUS       current
    DESCRIPTION
        "Cisco UCS sw:AccessEp:peerChassisId managed object property"
    ::= { cucsSwAccessEpEntry 21 }

cucsSwAccessEpLc OBJECT-TYPE
    SYNTAX       CucsSwPIoEpLc
    MAX-ACCESS   read-only
    STATUS       current
    DESCRIPTION
        "Cisco UCS sw:AccessEp:lc managed object property"
    ::= { cucsSwAccessEpEntry 22 }

cucsSwEnvStatsTable OBJECT-TYPE
    SYNTAX           SEQUENCE OF CucsSwEnvStatsEntry
    MAX-ACCESS       not-accessible
    STATUS           current
    DESCRIPTION
        "Cisco UCS sw:EnvStats managed object table"
    ::= { cucsSwObjects 4 }

cucsSwEnvStatsEntry OBJECT-TYPE
    SYNTAX           CucsSwEnvStatsEntry
    MAX-ACCESS       not-accessible
    STATUS           current
    DESCRIPTION
        "Entry for the cucsSwEnvStatsTable table."
    INDEX { cucsSwEnvStatsInstanceId }
    ::= { cucsSwEnvStatsTable 1 }

CucsSwEnvStatsEntry ::= SEQUENCE {
    cucsSwEnvStatsInstanceId                                         CucsManagedObjectId,
    cucsSwEnvStatsDn                                                 CucsManagedObjectDn,
    cucsSwEnvStatsRn                                                 SnmpAdminString,
    cucsSwEnvStatsFanCtrlrInlet1                                     INTEGER,
    cucsSwEnvStatsFanCtrlrInlet1Avg                                  INTEGER,
    cucsSwEnvStatsFanCtrlrInlet1Max                                  INTEGER,
    cucsSwEnvStatsFanCtrlrInlet1Min                                  INTEGER,
    cucsSwEnvStatsFanCtrlrInlet2                                     INTEGER,
    cucsSwEnvStatsFanCtrlrInlet2Avg                                  INTEGER,
    cucsSwEnvStatsFanCtrlrInlet2Max                                  INTEGER,
    cucsSwEnvStatsFanCtrlrInlet2Min                                  INTEGER,
    cucsSwEnvStatsFanCtrlrInlet3                                     INTEGER,
    cucsSwEnvStatsFanCtrlrInlet3Avg                                  INTEGER,
    cucsSwEnvStatsFanCtrlrInlet3Max                                  INTEGER,
    cucsSwEnvStatsFanCtrlrInlet3Min                                  INTEGER,
    cucsSwEnvStatsFanCtrlrInlet4                                     INTEGER,
    cucsSwEnvStatsFanCtrlrInlet4Avg                                  INTEGER,
    cucsSwEnvStatsFanCtrlrInlet4Max                                  INTEGER,
    cucsSwEnvStatsFanCtrlrInlet4Min                                  INTEGER,
    cucsSwEnvStatsIntervals                                          Gauge32,
    cucsSwEnvStatsMainBoardOutlet1                                   INTEGER,
    cucsSwEnvStatsMainBoardOutlet1Avg                                INTEGER,
    cucsSwEnvStatsMainBoardOutlet1Max                                INTEGER,
    cucsSwEnvStatsMainBoardOutlet1Min                                INTEGER,
    cucsSwEnvStatsMainBoardOutlet2                                   INTEGER,
    cucsSwEnvStatsMainBoardOutlet2Avg                                INTEGER,
    cucsSwEnvStatsMainBoardOutlet2Max                                INTEGER,
    cucsSwEnvStatsMainBoardOutlet2Min                                INTEGER,
    cucsSwEnvStatsPsuCtrlrInlet1                                     INTEGER,
    cucsSwEnvStatsPsuCtrlrInlet1Avg                                  INTEGER,
    cucsSwEnvStatsPsuCtrlrInlet1Max                                  INTEGER,
    cucsSwEnvStatsPsuCtrlrInlet1Min                                  INTEGER,
    cucsSwEnvStatsPsuCtrlrInlet2                                     INTEGER,
    cucsSwEnvStatsPsuCtrlrInlet2Avg                                  INTEGER,
    cucsSwEnvStatsPsuCtrlrInlet2Max                                  INTEGER,
    cucsSwEnvStatsPsuCtrlrInlet2Min                                  INTEGER,
    cucsSwEnvStatsSuspect                                            TruthValue,
    cucsSwEnvStatsThresholded                                        CucsSwEnvStatsThresholded,
    cucsSwEnvStatsTimeCollected                                      DateAndTime,
    cucsSwEnvStatsUpdate                                             Gauge32
}

cucsSwEnvStatsInstanceId OBJECT-TYPE
    SYNTAX       CucsManagedObjectId
    MAX-ACCESS   not-accessible
    STATUS       current
    DESCRIPTION
        "Instance identifier of the managed object."
    ::= { cucsSwEnvStatsEntry 1 }

cucsSwEnvStatsDn OBJECT-TYPE
    SYNTAX       CucsManagedObjectDn
    MAX-ACCESS   read-only
    STATUS       current
    DESCRIPTION
        "Cisco UCS sw:EnvStats:dn managed object property"
    ::= { cucsSwEnvStatsEntry 2 }

cucsSwEnvStatsRn OBJECT-TYPE
    SYNTAX       SnmpAdminString
    MAX-ACCESS   read-only
    STATUS       current
    DESCRIPTION
        "Cisco UCS sw:EnvStats:rn managed object property"
    ::= { cucsSwEnvStatsEntry 3 }

cucsSwEnvStatsFanCtrlrInlet1 OBJECT-TYPE
    SYNTAX       INTEGER
    MAX-ACCESS   read-only
    STATUS       current
    DESCRIPTION
        "Cisco UCS sw:EnvStats:fanCtrlrInlet1 managed object property"
    ::= { cucsSwEnvStatsEntry 4 }

cucsSwEnvStatsFanCtrlrInlet1Avg OBJECT-TYPE
    SYNTAX       INTEGER
    MAX-ACCESS   read-only
    STATUS       current
    DESCRIPTION
        "Cisco UCS sw:EnvStats:fanCtrlrInlet1Avg managed object property"
    ::= { cucsSwEnvStatsEntry 5 }

cucsSwEnvStatsFanCtrlrInlet1Max OBJECT-TYPE
    SYNTAX       INTEGER
    MAX-ACCESS   read-only
    STATUS       current
    DESCRIPTION
        "Cisco UCS sw:EnvStats:fanCtrlrInlet1Max managed object property"
    ::= { cucsSwEnvStatsEntry 6 }

cucsSwEnvStatsFanCtrlrInlet1Min OBJECT-TYPE
    SYNTAX       INTEGER
    MAX-ACCESS   read-only
    STATUS       current
    DESCRIPTION
        "Cisco UCS sw:EnvStats:fanCtrlrInlet1Min managed object property"
    ::= { cucsSwEnvStatsEntry 7 }

cucsSwEnvStatsFanCtrlrInlet2 OBJECT-TYPE
    SYNTAX       INTEGER
    MAX-ACCESS   read-only
    STATUS       current
    DESCRIPTION
        "Cisco UCS sw:EnvStats:fanCtrlrInlet2 managed object property"
    ::= { cucsSwEnvStatsEntry 8 }

cucsSwEnvStatsFanCtrlrInlet2Avg OBJECT-TYPE
    SYNTAX       INTEGER
    MAX-ACCESS   read-only
    STATUS       current
    DESCRIPTION
        "Cisco UCS sw:EnvStats:fanCtrlrInlet2Avg managed object property"
    ::= { cucsSwEnvStatsEntry 9 }

cucsSwEnvStatsFanCtrlrInlet2Max OBJECT-TYPE
    SYNTAX       INTEGER
    MAX-ACCESS   read-only
    STATUS       current
    DESCRIPTION
        "Cisco UCS sw:EnvStats:fanCtrlrInlet2Max managed object property"
    ::= { cucsSwEnvStatsEntry 10 }

cucsSwEnvStatsFanCtrlrInlet2Min OBJECT-TYPE
    SYNTAX       INTEGER
    MAX-ACCESS   read-only
    STATUS       current
    DESCRIPTION
        "Cisco UCS sw:EnvStats:fanCtrlrInlet2Min managed object property"
    ::= { cucsSwEnvStatsEntry 11 }

cucsSwEnvStatsFanCtrlrInlet3 OBJECT-TYPE
    SYNTAX       INTEGER
    MAX-ACCESS   read-only
    STATUS       current
    DESCRIPTION
        "Cisco UCS sw:EnvStats:fanCtrlrInlet3 managed object property"
    ::= { cucsSwEnvStatsEntry 12 }

cucsSwEnvStatsFanCtrlrInlet3Avg OBJECT-TYPE
    SYNTAX       INTEGER
    MAX-ACCESS   read-only
    STATUS       current
    DESCRIPTION
        "Cisco UCS sw:EnvStats:fanCtrlrInlet3Avg managed object property"
    ::= { cucsSwEnvStatsEntry 13 }

cucsSwEnvStatsFanCtrlrInlet3Max OBJECT-TYPE
    SYNTAX       INTEGER
    MAX-ACCESS   read-only
    STATUS       current
    DESCRIPTION
        "Cisco UCS sw:EnvStats:fanCtrlrInlet3Max managed object property"
    ::= { cucsSwEnvStatsEntry 14 }

cucsSwEnvStatsFanCtrlrInlet3Min OBJECT-TYPE
    SYNTAX       INTEGER
    MAX-ACCESS   read-only
    STATUS       current
    DESCRIPTION
        "Cisco UCS sw:EnvStats:fanCtrlrInlet3Min managed object property"
    ::= { cucsSwEnvStatsEntry 15 }

cucsSwEnvStatsFanCtrlrInlet4 OBJECT-TYPE
    SYNTAX       INTEGER
    MAX-ACCESS   read-only
    STATUS       current
    DESCRIPTION
        "Cisco UCS sw:EnvStats:fanCtrlrInlet4 managed object property"
    ::= { cucsSwEnvStatsEntry 16 }

cucsSwEnvStatsFanCtrlrInlet4Avg OBJECT-TYPE
    SYNTAX       INTEGER
    MAX-ACCESS   read-only
    STATUS       current
    DESCRIPTION
        "Cisco UCS sw:EnvStats:fanCtrlrInlet4Avg managed object property"
    ::= { cucsSwEnvStatsEntry 17 }

cucsSwEnvStatsFanCtrlrInlet4Max OBJECT-TYPE
    SYNTAX       INTEGER
    MAX-ACCESS   read-only
    STATUS       current
    DESCRIPTION
        "Cisco UCS sw:EnvStats:fanCtrlrInlet4Max managed object property"
    ::= { cucsSwEnvStatsEntry 18 }

cucsSwEnvStatsFanCtrlrInlet4Min OBJECT-TYPE
    SYNTAX       INTEGER
    MAX-ACCESS   read-only
    STATUS       current
    DESCRIPTION
        "Cisco UCS sw:EnvStats:fanCtrlrInlet4Min managed object property"
    ::= { cucsSwEnvStatsEntry 19 }

cucsSwEnvStatsIntervals OBJECT-TYPE
    SYNTAX       Gauge32
    MAX-ACCESS   read-only
    STATUS       current
    DESCRIPTION
        "Cisco UCS sw:EnvStats:intervals managed object property"
    ::= { cucsSwEnvStatsEntry 20 }

cucsSwEnvStatsMainBoardOutlet1 OBJECT-TYPE
    SYNTAX       INTEGER
    MAX-ACCESS   read-only
    STATUS       current
    DESCRIPTION
        "Cisco UCS sw:EnvStats:mainBoardOutlet1 managed object property"
    ::= { cucsSwEnvStatsEntry 21 }

cucsSwEnvStatsMainBoardOutlet1Avg OBJECT-TYPE
    SYNTAX       INTEGER
    MAX-ACCESS   read-only
    STATUS       current
    DESCRIPTION
        "Cisco UCS sw:EnvStats:mainBoardOutlet1Avg managed
        object property"
    ::= { cucsSwEnvStatsEntry 22 }

cucsSwEnvStatsMainBoardOutlet1Max OBJECT-TYPE
    SYNTAX       INTEGER
    MAX-ACCESS   read-only
    STATUS       current
    DESCRIPTION
        "Cisco UCS sw:EnvStats:mainBoardOutlet1Max managed
        object property"
    ::= { cucsSwEnvStatsEntry 23 }

cucsSwEnvStatsMainBoardOutlet1Min OBJECT-TYPE
    SYNTAX       INTEGER
    MAX-ACCESS   read-only
    STATUS       current
    DESCRIPTION
        "Cisco UCS sw:EnvStats:mainBoardOutlet1Min managed
        object property"
    ::= { cucsSwEnvStatsEntry 24 }

cucsSwEnvStatsMainBoardOutlet2 OBJECT-TYPE
    SYNTAX       INTEGER
    MAX-ACCESS   read-only
    STATUS       current
    DESCRIPTION
        "Cisco UCS sw:EnvStats:mainBoardOutlet2 managed object property"
    ::= { cucsSwEnvStatsEntry 25 }

cucsSwEnvStatsMainBoardOutlet2Avg OBJECT-TYPE
    SYNTAX       INTEGER
    MAX-ACCESS   read-only
    STATUS       current
    DESCRIPTION
        "Cisco UCS sw:EnvStats:mainBoardOutlet2Avg managed
        object property"
    ::= { cucsSwEnvStatsEntry 26 }

cucsSwEnvStatsMainBoardOutlet2Max OBJECT-TYPE
    SYNTAX       INTEGER
    MAX-ACCESS   read-only
    STATUS       current
    DESCRIPTION
        "Cisco UCS sw:EnvStats:mainBoardOutlet2Max managed
        object property"
    ::= { cucsSwEnvStatsEntry 27 }

cucsSwEnvStatsMainBoardOutlet2Min OBJECT-TYPE
    SYNTAX       INTEGER
    MAX-ACCESS   read-only
    STATUS       current
    DESCRIPTION
        "Cisco UCS sw:EnvStats:mainBoardOutlet2Min managed
        object property"
    ::= { cucsSwEnvStatsEntry 28 }

cucsSwEnvStatsPsuCtrlrInlet1 OBJECT-TYPE
    SYNTAX       INTEGER
    MAX-ACCESS   read-only
    STATUS       current
    DESCRIPTION
        "Cisco UCS sw:EnvStats:psuCtrlrInlet1 managed object property"
    ::= { cucsSwEnvStatsEntry 29 }

cucsSwEnvStatsPsuCtrlrInlet1Avg OBJECT-TYPE
    SYNTAX       INTEGER
    MAX-ACCESS   read-only
    STATUS       current
    DESCRIPTION
        "Cisco UCS sw:EnvStats:psuCtrlrInlet1Avg managed object property"
    ::= { cucsSwEnvStatsEntry 30 }

cucsSwEnvStatsPsuCtrlrInlet1Max OBJECT-TYPE
    SYNTAX       INTEGER
    MAX-ACCESS   read-only
    STATUS       current
    DESCRIPTION
        "Cisco UCS sw:EnvStats:psuCtrlrInlet1Max managed object property"
    ::= { cucsSwEnvStatsEntry 31 }

cucsSwEnvStatsPsuCtrlrInlet1Min OBJECT-TYPE
    SYNTAX       INTEGER
    MAX-ACCESS   read-only
    STATUS       current
    DESCRIPTION
        "Cisco UCS sw:EnvStats:psuCtrlrInlet1Min managed object property"
    ::= { cucsSwEnvStatsEntry 32 }

cucsSwEnvStatsPsuCtrlrInlet2 OBJECT-TYPE
    SYNTAX       INTEGER
    MAX-ACCESS   read-only
    STATUS       current
    DESCRIPTION
        "Cisco UCS sw:EnvStats:psuCtrlrInlet2 managed object property"
    ::= { cucsSwEnvStatsEntry 33 }

cucsSwEnvStatsPsuCtrlrInlet2Avg OBJECT-TYPE
    SYNTAX       INTEGER
    MAX-ACCESS   read-only
    STATUS       current
    DESCRIPTION
        "Cisco UCS sw:EnvStats:psuCtrlrInlet2Avg managed object property"
    ::= { cucsSwEnvStatsEntry 34 }

cucsSwEnvStatsPsuCtrlrInlet2Max OBJECT-TYPE
    SYNTAX       INTEGER
    MAX-ACCESS   read-only
    STATUS       current
    DESCRIPTION
        "Cisco UCS sw:EnvStats:psuCtrlrInlet2Max managed object property"
    ::= { cucsSwEnvStatsEntry 35 }

cucsSwEnvStatsPsuCtrlrInlet2Min OBJECT-TYPE
    SYNTAX       INTEGER
    MAX-ACCESS   read-only
    STATUS       current
    DESCRIPTION
        "Cisco UCS sw:EnvStats:psuCtrlrInlet2Min managed object property"
    ::= { cucsSwEnvStatsEntry 36 }

cucsSwEnvStatsSuspect OBJECT-TYPE
    SYNTAX       TruthValue
    MAX-ACCESS   read-only
    STATUS       current
    DESCRIPTION
        "Cisco UCS sw:EnvStats:suspect managed object property"
    ::= { cucsSwEnvStatsEntry 37 }

cucsSwEnvStatsThresholded OBJECT-TYPE
    SYNTAX       CucsSwEnvStatsThresholded
    MAX-ACCESS   read-only
    STATUS       current
    DESCRIPTION
        "Cisco UCS sw:EnvStats:thresholded managed object property"
    ::= { cucsSwEnvStatsEntry 38 }

cucsSwEnvStatsTimeCollected OBJECT-TYPE
    SYNTAX       DateAndTime
    MAX-ACCESS   read-only
    STATUS       current
    DESCRIPTION
        "Cisco UCS sw:EnvStats:timeCollected managed object property"
    ::= { cucsSwEnvStatsEntry 39 }

cucsSwEnvStatsUpdate OBJECT-TYPE
    SYNTAX       Gauge32
    MAX-ACCESS   read-only
    STATUS       current
    DESCRIPTION
        "Cisco UCS sw:EnvStats:update managed object property"
    ::= { cucsSwEnvStatsEntry 40 }

cucsSwEnvStatsHistTable OBJECT-TYPE
    SYNTAX           SEQUENCE OF CucsSwEnvStatsHistEntry
    MAX-ACCESS       not-accessible
    STATUS           current
    DESCRIPTION
        "Cisco UCS sw:EnvStatsHist managed object table"
    ::= { cucsSwObjects 5 }

cucsSwEnvStatsHistEntry OBJECT-TYPE
    SYNTAX           CucsSwEnvStatsHistEntry
    MAX-ACCESS       not-accessible
    STATUS           current
    DESCRIPTION
        "Entry for the cucsSwEnvStatsHistTable table."
    INDEX { cucsSwEnvStatsHistInstanceId }
    ::= { cucsSwEnvStatsHistTable 1 }

CucsSwEnvStatsHistEntry ::= SEQUENCE {
    cucsSwEnvStatsHistInstanceId                                     CucsManagedObjectId,
    cucsSwEnvStatsHistDn                                             CucsManagedObjectDn,
    cucsSwEnvStatsHistRn                                             SnmpAdminString,
    cucsSwEnvStatsHistFanCtrlrInlet1                                 INTEGER,
    cucsSwEnvStatsHistFanCtrlrInlet1Avg                              INTEGER,
    cucsSwEnvStatsHistFanCtrlrInlet1Max                              INTEGER,
    cucsSwEnvStatsHistFanCtrlrInlet1Min                              INTEGER,
    cucsSwEnvStatsHistFanCtrlrInlet2                                 INTEGER,
    cucsSwEnvStatsHistFanCtrlrInlet2Avg                              INTEGER,
    cucsSwEnvStatsHistFanCtrlrInlet2Max                              INTEGER,
    cucsSwEnvStatsHistFanCtrlrInlet2Min                              INTEGER,
    cucsSwEnvStatsHistFanCtrlrInlet3                                 INTEGER,
    cucsSwEnvStatsHistFanCtrlrInlet3Avg                              INTEGER,
    cucsSwEnvStatsHistFanCtrlrInlet3Max                              INTEGER,
    cucsSwEnvStatsHistFanCtrlrInlet3Min                              INTEGER,
    cucsSwEnvStatsHistFanCtrlrInlet4                                 INTEGER,
    cucsSwEnvStatsHistFanCtrlrInlet4Avg                              INTEGER,
    cucsSwEnvStatsHistFanCtrlrInlet4Max                              INTEGER,
    cucsSwEnvStatsHistFanCtrlrInlet4Min                              INTEGER,
    cucsSwEnvStatsHistId                                             Unsigned64,
    cucsSwEnvStatsHistMainBoardOutlet1                               INTEGER,
    cucsSwEnvStatsHistMainBoardOutlet1Avg                            INTEGER,
    cucsSwEnvStatsHistMainBoardOutlet1Max                            INTEGER,
    cucsSwEnvStatsHistMainBoardOutlet1Min                            INTEGER,
    cucsSwEnvStatsHistMainBoardOutlet2                               INTEGER,
    cucsSwEnvStatsHistMainBoardOutlet2Avg                            INTEGER,
    cucsSwEnvStatsHistMainBoardOutlet2Max                            INTEGER,
    cucsSwEnvStatsHistMainBoardOutlet2Min                            INTEGER,
    cucsSwEnvStatsHistMostRecent                                     TruthValue,
    cucsSwEnvStatsHistPsuCtrlrInlet1                                 INTEGER,
    cucsSwEnvStatsHistPsuCtrlrInlet1Avg                              INTEGER,
    cucsSwEnvStatsHistPsuCtrlrInlet1Max                              INTEGER,
    cucsSwEnvStatsHistPsuCtrlrInlet1Min                              INTEGER,
    cucsSwEnvStatsHistPsuCtrlrInlet2                                 INTEGER,
    cucsSwEnvStatsHistPsuCtrlrInlet2Avg                              INTEGER,
    cucsSwEnvStatsHistPsuCtrlrInlet2Max                              INTEGER,
    cucsSwEnvStatsHistPsuCtrlrInlet2Min                              INTEGER,
    cucsSwEnvStatsHistSuspect                                        TruthValue,
    cucsSwEnvStatsHistThresholded                                    CucsSwEnvStatsHistThresholded,
    cucsSwEnvStatsHistTimeCollected                                  DateAndTime
}

cucsSwEnvStatsHistInstanceId OBJECT-TYPE
    SYNTAX       CucsManagedObjectId
    MAX-ACCESS   not-accessible
    STATUS       current
    DESCRIPTION
        "Instance identifier of the managed object."
    ::= { cucsSwEnvStatsHistEntry 1 }

cucsSwEnvStatsHistDn OBJECT-TYPE
    SYNTAX       CucsManagedObjectDn
    MAX-ACCESS   read-only
    STATUS       current
    DESCRIPTION
        "Cisco UCS sw:EnvStatsHist:dn managed object property"
    ::= { cucsSwEnvStatsHistEntry 2 }

cucsSwEnvStatsHistRn OBJECT-TYPE
    SYNTAX       SnmpAdminString
    MAX-ACCESS   read-only
    STATUS       current
    DESCRIPTION
        "Cisco UCS sw:EnvStatsHist:rn managed object property"
    ::= { cucsSwEnvStatsHistEntry 3 }

cucsSwEnvStatsHistFanCtrlrInlet1 OBJECT-TYPE
    SYNTAX       INTEGER
    MAX-ACCESS   read-only
    STATUS       current
    DESCRIPTION
        "Cisco UCS sw:EnvStatsHist:fanCtrlrInlet1 managed object property"
    ::= { cucsSwEnvStatsHistEntry 4 }

cucsSwEnvStatsHistFanCtrlrInlet1Avg OBJECT-TYPE
    SYNTAX       INTEGER
    MAX-ACCESS   read-only
    STATUS       current
    DESCRIPTION
        "Cisco UCS sw:EnvStatsHist:fanCtrlrInlet1Avg managed
        object property"
    ::= { cucsSwEnvStatsHistEntry 5 }

cucsSwEnvStatsHistFanCtrlrInlet1Max OBJECT-TYPE
    SYNTAX       INTEGER
    MAX-ACCESS   read-only
    STATUS       current
    DESCRIPTION
        "Cisco UCS sw:EnvStatsHist:fanCtrlrInlet1Max managed
        object property"
    ::= { cucsSwEnvStatsHistEntry 6 }

cucsSwEnvStatsHistFanCtrlrInlet1Min OBJECT-TYPE
    SYNTAX       INTEGER
    MAX-ACCESS   read-only
    STATUS       current
    DESCRIPTION
        "Cisco UCS sw:EnvStatsHist:fanCtrlrInlet1Min managed
        object property"
    ::= { cucsSwEnvStatsHistEntry 7 }

cucsSwEnvStatsHistFanCtrlrInlet2 OBJECT-TYPE
    SYNTAX       INTEGER
    MAX-ACCESS   read-only
    STATUS       current
    DESCRIPTION
        "Cisco UCS sw:EnvStatsHist:fanCtrlrInlet2 managed object property"
    ::= { cucsSwEnvStatsHistEntry 8 }

cucsSwEnvStatsHistFanCtrlrInlet2Avg OBJECT-TYPE
    SYNTAX       INTEGER
    MAX-ACCESS   read-only
    STATUS       current
    DESCRIPTION
        "Cisco UCS sw:EnvStatsHist:fanCtrlrInlet2Avg managed
        object property"
    ::= { cucsSwEnvStatsHistEntry 9 }

cucsSwEnvStatsHistFanCtrlrInlet2Max OBJECT-TYPE
    SYNTAX       INTEGER
    MAX-ACCESS   read-only
    STATUS       current
    DESCRIPTION
        "Cisco UCS sw:EnvStatsHist:fanCtrlrInlet2Max managed
        object property"
    ::= { cucsSwEnvStatsHistEntry 10 }

cucsSwEnvStatsHistFanCtrlrInlet2Min OBJECT-TYPE
    SYNTAX       INTEGER
    MAX-ACCESS   read-only
    STATUS       current
    DESCRIPTION
        "Cisco UCS sw:EnvStatsHist:fanCtrlrInlet2Min managed
        object property"
    ::= { cucsSwEnvStatsHistEntry 11 }

cucsSwEnvStatsHistFanCtrlrInlet3 OBJECT-TYPE
    SYNTAX       INTEGER
    MAX-ACCESS   read-only
    STATUS       current
    DESCRIPTION
        "Cisco UCS sw:EnvStatsHist:fanCtrlrInlet3 managed object property"
    ::= { cucsSwEnvStatsHistEntry 12 }

cucsSwEnvStatsHistFanCtrlrInlet3Avg OBJECT-TYPE
    SYNTAX       INTEGER
    MAX-ACCESS   read-only
    STATUS       current
    DESCRIPTION
        "Cisco UCS sw:EnvStatsHist:fanCtrlrInlet3Avg managed
        object property"
    ::= { cucsSwEnvStatsHistEntry 13 }

cucsSwEnvStatsHistFanCtrlrInlet3Max OBJECT-TYPE
    SYNTAX       INTEGER
    MAX-ACCESS   read-only
    STATUS       current
    DESCRIPTION
        "Cisco UCS sw:EnvStatsHist:fanCtrlrInlet3Max managed
        object property"
    ::= { cucsSwEnvStatsHistEntry 14 }

cucsSwEnvStatsHistFanCtrlrInlet3Min OBJECT-TYPE
    SYNTAX       INTEGER
    MAX-ACCESS   read-only
    STATUS       current
    DESCRIPTION
        "Cisco UCS sw:EnvStatsHist:fanCtrlrInlet3Min managed
        object property"
    ::= { cucsSwEnvStatsHistEntry 15 }

cucsSwEnvStatsHistFanCtrlrInlet4 OBJECT-TYPE
    SYNTAX       INTEGER
    MAX-ACCESS   read-only
    STATUS       current
    DESCRIPTION
        "Cisco UCS sw:EnvStatsHist:fanCtrlrInlet4 managed object property"
    ::= { cucsSwEnvStatsHistEntry 16 }

cucsSwEnvStatsHistFanCtrlrInlet4Avg OBJECT-TYPE
    SYNTAX       INTEGER
    MAX-ACCESS   read-only
    STATUS       current
    DESCRIPTION
        "Cisco UCS sw:EnvStatsHist:fanCtrlrInlet4Avg managed
        object property"
    ::= { cucsSwEnvStatsHistEntry 17 }

cucsSwEnvStatsHistFanCtrlrInlet4Max OBJECT-TYPE
    SYNTAX       INTEGER
    MAX-ACCESS   read-only
    STATUS       current
    DESCRIPTION
        "Cisco UCS sw:EnvStatsHist:fanCtrlrInlet4Max managed
        object property"
    ::= { cucsSwEnvStatsHistEntry 18 }

cucsSwEnvStatsHistFanCtrlrInlet4Min OBJECT-TYPE
    SYNTAX       INTEGER
    MAX-ACCESS   read-only
    STATUS       current
    DESCRIPTION
        "Cisco UCS sw:EnvStatsHist:fanCtrlrInlet4Min managed
        object property"
    ::= { cucsSwEnvStatsHistEntry 19 }

cucsSwEnvStatsHistId OBJECT-TYPE
    SYNTAX       Unsigned64
    MAX-ACCESS   read-only
    STATUS       current
    DESCRIPTION
        "Cisco UCS sw:EnvStatsHist:id managed object property"
    ::= { cucsSwEnvStatsHistEntry 20 }

cucsSwEnvStatsHistMainBoardOutlet1 OBJECT-TYPE
    SYNTAX       INTEGER
    MAX-ACCESS   read-only
    STATUS       current
    DESCRIPTION
        "Cisco UCS sw:EnvStatsHist:mainBoardOutlet1 managed
        object property"
    ::= { cucsSwEnvStatsHistEntry 21 }

cucsSwEnvStatsHistMainBoardOutlet1Avg OBJECT-TYPE
    SYNTAX       INTEGER
    MAX-ACCESS   read-only
    STATUS       current
    DESCRIPTION
        "Cisco UCS sw:EnvStatsHist:mainBoardOutlet1Avg
        managed object property"
    ::= { cucsSwEnvStatsHistEntry 22 }

cucsSwEnvStatsHistMainBoardOutlet1Max OBJECT-TYPE
    SYNTAX       INTEGER
    MAX-ACCESS   read-only
    STATUS       current
    DESCRIPTION
        "Cisco UCS sw:EnvStatsHist:mainBoardOutlet1Max
        managed object property"
    ::= { cucsSwEnvStatsHistEntry 23 }

cucsSwEnvStatsHistMainBoardOutlet1Min OBJECT-TYPE
    SYNTAX       INTEGER
    MAX-ACCESS   read-only
    STATUS       current
    DESCRIPTION
        "Cisco UCS sw:EnvStatsHist:mainBoardOutlet1Min
        managed object property"
    ::= { cucsSwEnvStatsHistEntry 24 }

cucsSwEnvStatsHistMainBoardOutlet2 OBJECT-TYPE
    SYNTAX       INTEGER
    MAX-ACCESS   read-only
    STATUS       current
    DESCRIPTION
        "Cisco UCS sw:EnvStatsHist:mainBoardOutlet2 managed
        object property"
    ::= { cucsSwEnvStatsHistEntry 25 }

cucsSwEnvStatsHistMainBoardOutlet2Avg OBJECT-TYPE
    SYNTAX       INTEGER
    MAX-ACCESS   read-only
    STATUS       current
    DESCRIPTION
        "Cisco UCS sw:EnvStatsHist:mainBoardOutlet2Avg
        managed object property"
    ::= { cucsSwEnvStatsHistEntry 26 }

cucsSwEnvStatsHistMainBoardOutlet2Max OBJECT-TYPE
    SYNTAX       INTEGER
    MAX-ACCESS   read-only
    STATUS       current
    DESCRIPTION
        "Cisco UCS sw:EnvStatsHist:mainBoardOutlet2Max
        managed object property"
    ::= { cucsSwEnvStatsHistEntry 27 }

cucsSwEnvStatsHistMainBoardOutlet2Min OBJECT-TYPE
    SYNTAX       INTEGER
    MAX-ACCESS   read-only
    STATUS       current
    DESCRIPTION
        "Cisco UCS sw:EnvStatsHist:mainBoardOutlet2Min
        managed object property"
    ::= { cucsSwEnvStatsHistEntry 28 }

cucsSwEnvStatsHistMostRecent OBJECT-TYPE
    SYNTAX       TruthValue
    MAX-ACCESS   read-only
    STATUS       current
    DESCRIPTION
        "Cisco UCS sw:EnvStatsHist:mostRecent managed object property"
    ::= { cucsSwEnvStatsHistEntry 29 }

cucsSwEnvStatsHistPsuCtrlrInlet1 OBJECT-TYPE
    SYNTAX       INTEGER
    MAX-ACCESS   read-only
    STATUS       current
    DESCRIPTION
        "Cisco UCS sw:EnvStatsHist:psuCtrlrInlet1 managed object property"
    ::= { cucsSwEnvStatsHistEntry 30 }

cucsSwEnvStatsHistPsuCtrlrInlet1Avg OBJECT-TYPE
    SYNTAX       INTEGER
    MAX-ACCESS   read-only
    STATUS       current
    DESCRIPTION
        "Cisco UCS sw:EnvStatsHist:psuCtrlrInlet1Avg managed
        object property"
    ::= { cucsSwEnvStatsHistEntry 31 }

cucsSwEnvStatsHistPsuCtrlrInlet1Max OBJECT-TYPE
    SYNTAX       INTEGER
    MAX-ACCESS   read-only
    STATUS       current
    DESCRIPTION
        "Cisco UCS sw:EnvStatsHist:psuCtrlrInlet1Max managed
        object property"
    ::= { cucsSwEnvStatsHistEntry 32 }

cucsSwEnvStatsHistPsuCtrlrInlet1Min OBJECT-TYPE
    SYNTAX       INTEGER
    MAX-ACCESS   read-only
    STATUS       current
    DESCRIPTION
        "Cisco UCS sw:EnvStatsHist:psuCtrlrInlet1Min managed
        object property"
    ::= { cucsSwEnvStatsHistEntry 33 }

cucsSwEnvStatsHistPsuCtrlrInlet2 OBJECT-TYPE
    SYNTAX       INTEGER
    MAX-ACCESS   read-only
    STATUS       current
    DESCRIPTION
        "Cisco UCS sw:EnvStatsHist:psuCtrlrInlet2 managed object property"
    ::= { cucsSwEnvStatsHistEntry 34 }

cucsSwEnvStatsHistPsuCtrlrInlet2Avg OBJECT-TYPE
    SYNTAX       INTEGER
    MAX-ACCESS   read-only
    STATUS       current
    DESCRIPTION
        "Cisco UCS sw:EnvStatsHist:psuCtrlrInlet2Avg managed
        object property"
    ::= { cucsSwEnvStatsHistEntry 35 }

cucsSwEnvStatsHistPsuCtrlrInlet2Max OBJECT-TYPE
    SYNTAX       INTEGER
    MAX-ACCESS   read-only
    STATUS       current
    DESCRIPTION
        "Cisco UCS sw:EnvStatsHist:psuCtrlrInlet2Max managed
        object property"
    ::= { cucsSwEnvStatsHistEntry 36 }

cucsSwEnvStatsHistPsuCtrlrInlet2Min OBJECT-TYPE
    SYNTAX       INTEGER
    MAX-ACCESS   read-only
    STATUS       current
    DESCRIPTION
        "Cisco UCS sw:EnvStatsHist:psuCtrlrInlet2Min managed
        object property"
    ::= { cucsSwEnvStatsHistEntry 37 }

cucsSwEnvStatsHistSuspect OBJECT-TYPE
    SYNTAX       TruthValue
    MAX-ACCESS   read-only
    STATUS       current
    DESCRIPTION
        "Cisco UCS sw:EnvStatsHist:suspect managed object property"
    ::= { cucsSwEnvStatsHistEntry 38 }

cucsSwEnvStatsHistThresholded OBJECT-TYPE
    SYNTAX       CucsSwEnvStatsHistThresholded
    MAX-ACCESS   read-only
    STATUS       current
    DESCRIPTION
        "Cisco UCS sw:EnvStatsHist:thresholded managed object property"
    ::= { cucsSwEnvStatsHistEntry 39 }

cucsSwEnvStatsHistTimeCollected OBJECT-TYPE
    SYNTAX       DateAndTime
    MAX-ACCESS   read-only
    STATUS       current
    DESCRIPTION
        "Cisco UCS sw:EnvStatsHist:timeCollected managed object property"
    ::= { cucsSwEnvStatsHistEntry 40 }

cucsSwEthEstcEpTable OBJECT-TYPE
    SYNTAX           SEQUENCE OF CucsSwEthEstcEpEntry
    MAX-ACCESS       not-accessible
    STATUS           current
    DESCRIPTION
        "Cisco UCS sw:EthEstcEp managed object table"
    ::= { cucsSwObjects 6 }

cucsSwEthEstcEpEntry OBJECT-TYPE
    SYNTAX           CucsSwEthEstcEpEntry
    MAX-ACCESS       not-accessible
    STATUS           current
    DESCRIPTION
        "Entry for the cucsSwEthEstcEpTable table."
    INDEX { cucsSwEthEstcEpInstanceId }
    ::= { cucsSwEthEstcEpTable 1 }

CucsSwEthEstcEpEntry ::= SEQUENCE {
    cucsSwEthEstcEpInstanceId                                        CucsManagedObjectId,
    cucsSwEthEstcEpDn                                                CucsManagedObjectDn,
    cucsSwEthEstcEpRn                                                SnmpAdminString,
    cucsSwEthEstcEpAdminState                                        CucsFabricAdminState,
    cucsSwEthEstcEpBorderPortId                                      Gauge32,
    cucsSwEthEstcEpBorderSlotId                                      Gauge32,
    cucsSwEthEstcEpChassisId                                         Gauge32,
    cucsSwEthEstcEpCosValue                                          Gauge32,
    cucsSwEthEstcEpEpDn                                              SnmpAdminString,
    cucsSwEthEstcEpIfRole                                            CucsNetworkPortRole,
    cucsSwEthEstcEpIfType                                            CucsSwPIoEpIfType,
    cucsSwEthEstcEpLocale                                            CucsSwEstcEpLocale,
    cucsSwEthEstcEpName                                              SnmpAdminString,
    cucsSwEthEstcEpPeerDn                                            SnmpAdminString,
    cucsSwEthEstcEpPeerPortId                                        Gauge32,
    cucsSwEthEstcEpPeerSlotId                                        Gauge32,
    cucsSwEthEstcEpPinGroupName                                      SnmpAdminString,
    cucsSwEthEstcEpPortId                                            Gauge32,
    cucsSwEthEstcEpPortMode                                          CucsFabricEthEstcPortMode,
    cucsSwEthEstcEpSlotId                                            Gauge32,
    cucsSwEthEstcEpSwitchId                                          CucsNetworkSwitchId,
    cucsSwEthEstcEpTransport                                         CucsSwEthEstcEpTransport,
    cucsSwEthEstcEpType                                              CucsNetworkConnectionType,
    cucsSwEthEstcEpAdminSpeed                                        CucsPortEthSpeed,
    cucsSwEthEstcEpPcId                                              Gauge32,
    cucsSwEthEstcEpPeerChassisId                                     Gauge32,
    cucsSwEthEstcEpCdp                                               CucsNwctrlAdminState,
    cucsSwEthEstcEpForgeMac                                          CucsDpsecForgedTransmit,
    cucsSwEthEstcEpUplinkFailAction                                  CucsNwctrlLinkFailAction,
    cucsSwEthEstcEpLc                                                CucsSwPIoEpLc
}

cucsSwEthEstcEpInstanceId OBJECT-TYPE
    SYNTAX       CucsManagedObjectId
    MAX-ACCESS   not-accessible
    STATUS       current
    DESCRIPTION
        "Instance identifier of the managed object."
    ::= { cucsSwEthEstcEpEntry 1 }

cucsSwEthEstcEpDn OBJECT-TYPE
    SYNTAX       CucsManagedObjectDn
    MAX-ACCESS   read-only
    STATUS       current
    DESCRIPTION
        "Cisco UCS sw:EthEstcEp:dn managed object property"
    ::= { cucsSwEthEstcEpEntry 2 }

cucsSwEthEstcEpRn OBJECT-TYPE
    SYNTAX       SnmpAdminString
    MAX-ACCESS   read-only
    STATUS       current
    DESCRIPTION
        "Cisco UCS sw:EthEstcEp:rn managed object property"
    ::= { cucsSwEthEstcEpEntry 3 }

cucsSwEthEstcEpAdminState OBJECT-TYPE
    SYNTAX       CucsFabricAdminState
    MAX-ACCESS   read-only
    STATUS       current
    DESCRIPTION
        "Cisco UCS sw:EthEstcEp:adminState managed object property"
    ::= { cucsSwEthEstcEpEntry 4 }

cucsSwEthEstcEpBorderPortId OBJECT-TYPE
    SYNTAX       Gauge32
    MAX-ACCESS   read-only
    STATUS       current
    DESCRIPTION
        "Cisco UCS sw:EthEstcEp:borderPortId managed object property"
    ::= { cucsSwEthEstcEpEntry 5 }

cucsSwEthEstcEpBorderSlotId OBJECT-TYPE
    SYNTAX       Gauge32
    MAX-ACCESS   read-only
    STATUS       current
    DESCRIPTION
        "Cisco UCS sw:EthEstcEp:borderSlotId managed object property"
    ::= { cucsSwEthEstcEpEntry 6 }

cucsSwEthEstcEpChassisId OBJECT-TYPE
    SYNTAX       Gauge32
    MAX-ACCESS   read-only
    STATUS       current
    DESCRIPTION
        "Cisco UCS sw:EthEstcEp:chassisId managed object property"
    ::= { cucsSwEthEstcEpEntry 7 }

cucsSwEthEstcEpCosValue OBJECT-TYPE
    SYNTAX       Gauge32
    MAX-ACCESS   read-only
    STATUS       current
    DESCRIPTION
        "Cisco UCS sw:EthEstcEp:cosValue managed object property"
    ::= { cucsSwEthEstcEpEntry 8 }

cucsSwEthEstcEpEpDn OBJECT-TYPE
    SYNTAX       SnmpAdminString
    MAX-ACCESS   read-only
    STATUS       current
    DESCRIPTION
        "Cisco UCS sw:EthEstcEp:epDn managed object property"
    ::= { cucsSwEthEstcEpEntry 9 }

cucsSwEthEstcEpIfRole OBJECT-TYPE
    SYNTAX       CucsNetworkPortRole
    MAX-ACCESS   read-only
    STATUS       current
    DESCRIPTION
        "Cisco UCS sw:EthEstcEp:ifRole managed object property"
    ::= { cucsSwEthEstcEpEntry 10 }

cucsSwEthEstcEpIfType OBJECT-TYPE
    SYNTAX       CucsSwPIoEpIfType
    MAX-ACCESS   read-only
    STATUS       current
    DESCRIPTION
        "Cisco UCS sw:EthEstcEp:ifType managed object property"
    ::= { cucsSwEthEstcEpEntry 11 }

cucsSwEthEstcEpLocale OBJECT-TYPE
    SYNTAX       CucsSwEstcEpLocale
    MAX-ACCESS   read-only
    STATUS       current
    DESCRIPTION
        "Cisco UCS sw:EthEstcEp:locale managed object property"
    ::= { cucsSwEthEstcEpEntry 12 }

cucsSwEthEstcEpName OBJECT-TYPE
    SYNTAX       SnmpAdminString
    MAX-ACCESS   read-only
    STATUS       current
    DESCRIPTION
        "Cisco UCS sw:EthEstcEp:name managed object property"
    ::= { cucsSwEthEstcEpEntry 13 }

cucsSwEthEstcEpPeerDn OBJECT-TYPE
    SYNTAX       SnmpAdminString
    MAX-ACCESS   read-only
    STATUS       current
    DESCRIPTION
        "Cisco UCS sw:EthEstcEp:peerDn managed object property"
    ::= { cucsSwEthEstcEpEntry 14 }

cucsSwEthEstcEpPeerPortId OBJECT-TYPE
    SYNTAX       Gauge32
    MAX-ACCESS   read-only
    STATUS       current
    DESCRIPTION
        "Cisco UCS sw:EthEstcEp:peerPortId managed object property"
    ::= { cucsSwEthEstcEpEntry 15 }

cucsSwEthEstcEpPeerSlotId OBJECT-TYPE
    SYNTAX       Gauge32
    MAX-ACCESS   read-only
    STATUS       current
    DESCRIPTION
        "Cisco UCS sw:EthEstcEp:peerSlotId managed object property"
    ::= { cucsSwEthEstcEpEntry 16 }

cucsSwEthEstcEpPinGroupName OBJECT-TYPE
    SYNTAX       SnmpAdminString
    MAX-ACCESS   read-only
    STATUS       current
    DESCRIPTION
        "Cisco UCS sw:EthEstcEp:pinGroupName managed object property"
    ::= { cucsSwEthEstcEpEntry 17 }

cucsSwEthEstcEpPortId OBJECT-TYPE
    SYNTAX       Gauge32
    MAX-ACCESS   read-only
    STATUS       current
    DESCRIPTION
        "Cisco UCS sw:EthEstcEp:portId managed object property"
    ::= { cucsSwEthEstcEpEntry 18 }

cucsSwEthEstcEpPortMode OBJECT-TYPE
    SYNTAX       CucsFabricEthEstcPortMode
    MAX-ACCESS   read-only
    STATUS       current
    DESCRIPTION
        "Cisco UCS sw:EthEstcEp:portMode managed object property"
    ::= { cucsSwEthEstcEpEntry 19 }

cucsSwEthEstcEpSlotId OBJECT-TYPE
    SYNTAX       Gauge32
    MAX-ACCESS   read-only
    STATUS       current
    DESCRIPTION
        "Cisco UCS sw:EthEstcEp:slotId managed object property"
    ::= { cucsSwEthEstcEpEntry 20 }

cucsSwEthEstcEpSwitchId OBJECT-TYPE
    SYNTAX       CucsNetworkSwitchId
    MAX-ACCESS   read-only
    STATUS       current
    DESCRIPTION
        "Cisco UCS sw:EthEstcEp:switchId managed object property"
    ::= { cucsSwEthEstcEpEntry 21 }

cucsSwEthEstcEpTransport OBJECT-TYPE
    SYNTAX       CucsSwEthEstcEpTransport
    MAX-ACCESS   read-only
    STATUS       current
    DESCRIPTION
        "Cisco UCS sw:EthEstcEp:transport managed object property"
    ::= { cucsSwEthEstcEpEntry 22 }

cucsSwEthEstcEpType OBJECT-TYPE
    SYNTAX       CucsNetworkConnectionType
    MAX-ACCESS   read-only
    STATUS       current
    DESCRIPTION
        "Cisco UCS sw:EthEstcEp:type managed object property"
    ::= { cucsSwEthEstcEpEntry 23 }

cucsSwEthEstcEpAdminSpeed OBJECT-TYPE
    SYNTAX       CucsPortEthSpeed
    MAX-ACCESS   read-only
    STATUS       current
    DESCRIPTION
        "Cisco UCS sw:EthEstcEp:adminSpeed managed object property"
    ::= { cucsSwEthEstcEpEntry 24 }

cucsSwEthEstcEpPcId OBJECT-TYPE
    SYNTAX       Gauge32
    MAX-ACCESS   read-only
    STATUS       current
    DESCRIPTION
        "Cisco UCS sw:EthEstcEp:pcId managed object property"
    ::= { cucsSwEthEstcEpEntry 25 }

cucsSwEthEstcEpPeerChassisId OBJECT-TYPE
    SYNTAX       Gauge32
    MAX-ACCESS   read-only
    STATUS       current
    DESCRIPTION
        "Cisco UCS sw:EthEstcEp:peerChassisId managed object property"
    ::= { cucsSwEthEstcEpEntry 26 }

cucsSwEthEstcEpCdp OBJECT-TYPE
    SYNTAX       CucsNwctrlAdminState
    MAX-ACCESS   read-only
    STATUS       current
    DESCRIPTION
        "Cisco UCS sw:EthEstcEp:cdp managed object property"
    ::= { cucsSwEthEstcEpEntry 27 }

cucsSwEthEstcEpForgeMac OBJECT-TYPE
    SYNTAX       CucsDpsecForgedTransmit
    MAX-ACCESS   read-only
    STATUS       current
    DESCRIPTION
        "Cisco UCS sw:EthEstcEp:forgeMac managed object property"
    ::= { cucsSwEthEstcEpEntry 28 }

cucsSwEthEstcEpUplinkFailAction OBJECT-TYPE
    SYNTAX       CucsNwctrlLinkFailAction
    MAX-ACCESS   read-only
    STATUS       current
    DESCRIPTION
        "Cisco UCS sw:EthEstcEp:uplinkFailAction managed object property"
    ::= { cucsSwEthEstcEpEntry 29 }

cucsSwEthEstcEpLc OBJECT-TYPE
    SYNTAX       CucsSwPIoEpLc
    MAX-ACCESS   read-only
    STATUS       current
    DESCRIPTION
        "Cisco UCS sw:EthEstcEp:lc managed object property"
    ::= { cucsSwEthEstcEpEntry 30 }

cucsSwEthEstcPcTable OBJECT-TYPE
    SYNTAX           SEQUENCE OF CucsSwEthEstcPcEntry
    MAX-ACCESS       not-accessible
    STATUS           current
    DESCRIPTION
        "Cisco UCS sw:EthEstcPc managed object table"
    ::= { cucsSwObjects 36 }

cucsSwEthEstcPcEntry OBJECT-TYPE
    SYNTAX           CucsSwEthEstcPcEntry
    MAX-ACCESS       not-accessible
    STATUS           current
    DESCRIPTION
        "Entry for the cucsSwEthEstcPcTable table."
    INDEX { cucsSwEthEstcPcInstanceId }
    ::= { cucsSwEthEstcPcTable 1 }

CucsSwEthEstcPcEntry ::= SEQUENCE {
    cucsSwEthEstcPcInstanceId                                        CucsManagedObjectId,
    cucsSwEthEstcPcDn                                                CucsManagedObjectDn,
    cucsSwEthEstcPcRn                                                SnmpAdminString,
    cucsSwEthEstcPcAdminSpeed                                        CucsPortEthSpeed,
    cucsSwEthEstcPcAdminState                                        CucsFabricAdminState,
    cucsSwEthEstcPcBorderPortId                                      Gauge32,
    cucsSwEthEstcPcBorderSlotId                                      Gauge32,
    cucsSwEthEstcPcCosValue                                          Gauge32,
    cucsSwEthEstcPcEpDn                                              SnmpAdminString,
    cucsSwEthEstcPcIfRole                                            CucsSwLanPcIfRole,
    cucsSwEthEstcPcIfType                                            CucsSwCIoEpIfType,
    cucsSwEthEstcPcLocale                                            CucsSwBorderPcLocale,
    cucsSwEthEstcPcMonTrafDir                                        CucsFabricTrafficDirection,
    cucsSwEthEstcPcName                                              SnmpAdminString,
    cucsSwEthEstcPcPeerDn                                            SnmpAdminString,
    cucsSwEthEstcPcPortId                                            Gauge32,
    cucsSwEthEstcPcPortMode                                          CucsFabricEthEstcPortMode,
    cucsSwEthEstcPcSwitchId                                          CucsNetworkSwitchId,
    cucsSwEthEstcPcTransport                                         CucsSwEthEstcPcTransport,
    cucsSwEthEstcPcType                                              CucsSwLanPcType,
    cucsSwEthEstcPcCdp                                               CucsNwctrlAdminState,
    cucsSwEthEstcPcForgeMac                                          CucsDpsecForgedTransmit,
    cucsSwEthEstcPcProtocol                                          CucsFabricEthPcProtocol,
    cucsSwEthEstcPcUplinkFailAction                                  CucsNwctrlLinkFailAction
}

cucsSwEthEstcPcInstanceId OBJECT-TYPE
    SYNTAX       CucsManagedObjectId
    MAX-ACCESS   not-accessible
    STATUS       current
    DESCRIPTION
        "Instance identifier of the managed object."
    ::= { cucsSwEthEstcPcEntry 1 }

cucsSwEthEstcPcDn OBJECT-TYPE
    SYNTAX       CucsManagedObjectDn
    MAX-ACCESS   read-only
    STATUS       current
    DESCRIPTION
        "Cisco UCS sw:EthEstcPc:dn managed object property"
    ::= { cucsSwEthEstcPcEntry 2 }

cucsSwEthEstcPcRn OBJECT-TYPE
    SYNTAX       SnmpAdminString
    MAX-ACCESS   read-only
    STATUS       current
    DESCRIPTION
        "Cisco UCS sw:EthEstcPc:rn managed object property"
    ::= { cucsSwEthEstcPcEntry 3 }

cucsSwEthEstcPcAdminSpeed OBJECT-TYPE
    SYNTAX       CucsPortEthSpeed
    MAX-ACCESS   read-only
    STATUS       current
    DESCRIPTION
        "Cisco UCS sw:EthEstcPc:adminSpeed managed object property"
    ::= { cucsSwEthEstcPcEntry 4 }

cucsSwEthEstcPcAdminState OBJECT-TYPE
    SYNTAX       CucsFabricAdminState
    MAX-ACCESS   read-only
    STATUS       current
    DESCRIPTION
        "Cisco UCS sw:EthEstcPc:adminState managed object property"
    ::= { cucsSwEthEstcPcEntry 5 }

cucsSwEthEstcPcBorderPortId OBJECT-TYPE
    SYNTAX       Gauge32
    MAX-ACCESS   read-only
    STATUS       current
    DESCRIPTION
        "Cisco UCS sw:EthEstcPc:borderPortId managed object property"
    ::= { cucsSwEthEstcPcEntry 6 }

cucsSwEthEstcPcBorderSlotId OBJECT-TYPE
    SYNTAX       Gauge32
    MAX-ACCESS   read-only
    STATUS       current
    DESCRIPTION
        "Cisco UCS sw:EthEstcPc:borderSlotId managed object property"
    ::= { cucsSwEthEstcPcEntry 7 }

cucsSwEthEstcPcCosValue OBJECT-TYPE
    SYNTAX       Gauge32
    MAX-ACCESS   read-only
    STATUS       current
    DESCRIPTION
        "Cisco UCS sw:EthEstcPc:cosValue managed object property"
    ::= { cucsSwEthEstcPcEntry 8 }

cucsSwEthEstcPcEpDn OBJECT-TYPE
    SYNTAX       SnmpAdminString
    MAX-ACCESS   read-only
    STATUS       current
    DESCRIPTION
        "Cisco UCS sw:EthEstcPc:epDn managed object property"
    ::= { cucsSwEthEstcPcEntry 9 }

cucsSwEthEstcPcIfRole OBJECT-TYPE
    SYNTAX       CucsSwLanPcIfRole
    MAX-ACCESS   read-only
    STATUS       current
    DESCRIPTION
        "Cisco UCS sw:EthEstcPc:ifRole managed object property"
    ::= { cucsSwEthEstcPcEntry 10 }

cucsSwEthEstcPcIfType OBJECT-TYPE
    SYNTAX       CucsSwCIoEpIfType
    MAX-ACCESS   read-only
    STATUS       current
    DESCRIPTION
        "Cisco UCS sw:EthEstcPc:ifType managed object property"
    ::= { cucsSwEthEstcPcEntry 11 }

cucsSwEthEstcPcLocale OBJECT-TYPE
    SYNTAX       CucsSwBorderPcLocale
    MAX-ACCESS   read-only
    STATUS       current
    DESCRIPTION
        "Cisco UCS sw:EthEstcPc:locale managed object property"
    ::= { cucsSwEthEstcPcEntry 12 }

cucsSwEthEstcPcMonTrafDir OBJECT-TYPE
    SYNTAX       CucsFabricTrafficDirection
    MAX-ACCESS   read-only
    STATUS       current
    DESCRIPTION
        "Cisco UCS sw:EthEstcPc:monTrafDir managed object property"
    ::= { cucsSwEthEstcPcEntry 13 }

cucsSwEthEstcPcName OBJECT-TYPE
    SYNTAX       SnmpAdminString
    MAX-ACCESS   read-only
    STATUS       current
    DESCRIPTION
        "Cisco UCS sw:EthEstcPc:name managed object property"
    ::= { cucsSwEthEstcPcEntry 14 }

cucsSwEthEstcPcPeerDn OBJECT-TYPE
    SYNTAX       SnmpAdminString
    MAX-ACCESS   read-only
    STATUS       current
    DESCRIPTION
        "Cisco UCS sw:EthEstcPc:peerDn managed object property"
    ::= { cucsSwEthEstcPcEntry 15 }

cucsSwEthEstcPcPortId OBJECT-TYPE
    SYNTAX       Gauge32
    MAX-ACCESS   read-only
    STATUS       current
    DESCRIPTION
        "Cisco UCS sw:EthEstcPc:portId managed object property"
    ::= { cucsSwEthEstcPcEntry 16 }

cucsSwEthEstcPcPortMode OBJECT-TYPE
    SYNTAX       CucsFabricEthEstcPortMode
    MAX-ACCESS   read-only
    STATUS       current
    DESCRIPTION
        "Cisco UCS sw:EthEstcPc:portMode managed object property"
    ::= { cucsSwEthEstcPcEntry 17 }

cucsSwEthEstcPcSwitchId OBJECT-TYPE
    SYNTAX       CucsNetworkSwitchId
    MAX-ACCESS   read-only
    STATUS       current
    DESCRIPTION
        "Cisco UCS sw:EthEstcPc:switchId managed object property"
    ::= { cucsSwEthEstcPcEntry 18 }

cucsSwEthEstcPcTransport OBJECT-TYPE
    SYNTAX       CucsSwEthEstcPcTransport
    MAX-ACCESS   read-only
    STATUS       current
    DESCRIPTION
        "Cisco UCS sw:EthEstcPc:transport managed object property"
    ::= { cucsSwEthEstcPcEntry 19 }

cucsSwEthEstcPcType OBJECT-TYPE
    SYNTAX       CucsSwLanPcType
    MAX-ACCESS   read-only
    STATUS       current
    DESCRIPTION
        "Cisco UCS sw:EthEstcPc:type managed object property"
    ::= { cucsSwEthEstcPcEntry 20 }

cucsSwEthEstcPcCdp OBJECT-TYPE
    SYNTAX       CucsNwctrlAdminState
    MAX-ACCESS   read-only
    STATUS       current
    DESCRIPTION
        "Cisco UCS sw:EthEstcPc:cdp managed object property"
    ::= { cucsSwEthEstcPcEntry 21 }

cucsSwEthEstcPcForgeMac OBJECT-TYPE
    SYNTAX       CucsDpsecForgedTransmit
    MAX-ACCESS   read-only
    STATUS       current
    DESCRIPTION
        "Cisco UCS sw:EthEstcPc:forgeMac managed object property"
    ::= { cucsSwEthEstcPcEntry 22 }

cucsSwEthEstcPcProtocol OBJECT-TYPE
    SYNTAX       CucsFabricEthPcProtocol
    MAX-ACCESS   read-only
    STATUS       current
    DESCRIPTION
        "Cisco UCS sw:EthEstcPc:protocol managed object property"
    ::= { cucsSwEthEstcPcEntry 23 }

cucsSwEthEstcPcUplinkFailAction OBJECT-TYPE
    SYNTAX       CucsNwctrlLinkFailAction
    MAX-ACCESS   read-only
    STATUS       current
    DESCRIPTION
        "Cisco UCS sw:EthEstcPc:uplinkFailAction managed object property"
    ::= { cucsSwEthEstcPcEntry 24 }

cucsSwEthLanBorderTable OBJECT-TYPE
    SYNTAX           SEQUENCE OF CucsSwEthLanBorderEntry
    MAX-ACCESS       not-accessible
    STATUS           current
    DESCRIPTION
        "Cisco UCS sw:EthLanBorder managed object table"
    ::= { cucsSwObjects 7 }

cucsSwEthLanBorderEntry OBJECT-TYPE
    SYNTAX           CucsSwEthLanBorderEntry
    MAX-ACCESS       not-accessible
    STATUS           current
    DESCRIPTION
        "Entry for the cucsSwEthLanBorderTable table."
    INDEX { cucsSwEthLanBorderInstanceId }
    ::= { cucsSwEthLanBorderTable 1 }

CucsSwEthLanBorderEntry ::= SEQUENCE {
    cucsSwEthLanBorderInstanceId                                     CucsManagedObjectId,
    cucsSwEthLanBorderDn                                             CucsManagedObjectDn,
    cucsSwEthLanBorderRn                                             SnmpAdminString,
    cucsSwEthLanBorderFsmDescr                                       SnmpAdminString,
    cucsSwEthLanBorderFsmPrev                                        SnmpAdminString,
    cucsSwEthLanBorderFsmProgr                                       Gauge32,
    cucsSwEthLanBorderFsmRmtInvErrCode                               Gauge32,
    cucsSwEthLanBorderFsmRmtInvErrDescr                              SnmpAdminString,
    cucsSwEthLanBorderFsmRmtInvRslt                                  CucsConditionRemoteInvRslt,
    cucsSwEthLanBorderFsmStageDescr                                  SnmpAdminString,
    cucsSwEthLanBorderFsmStamp                                       DateAndTime,
    cucsSwEthLanBorderFsmStatus                                      SnmpAdminString,
    cucsSwEthLanBorderFsmTry                                         Gauge32,
    cucsSwEthLanBorderLocale                                         CucsSwBorderDomainLocale,
    cucsSwEthLanBorderName                                           SnmpAdminString,
    cucsSwEthLanBorderSwitchId                                       CucsNetworkSwitchId,
    cucsSwEthLanBorderTransport                                      CucsSwEthLanBorderTransport,
    cucsSwEthLanBorderType                                           CucsSwLanBorderType
}

cucsSwEthLanBorderInstanceId OBJECT-TYPE
    SYNTAX       CucsManagedObjectId
    MAX-ACCESS   not-accessible
    STATUS       current
    DESCRIPTION
        "Instance identifier of the managed object."
    ::= { cucsSwEthLanBorderEntry 1 }

cucsSwEthLanBorderDn OBJECT-TYPE
    SYNTAX       CucsManagedObjectDn
    MAX-ACCESS   read-only
    STATUS       current
    DESCRIPTION
        "Cisco UCS sw:EthLanBorder:dn managed object property"
    ::= { cucsSwEthLanBorderEntry 2 }

cucsSwEthLanBorderRn OBJECT-TYPE
    SYNTAX       SnmpAdminString
    MAX-ACCESS   read-only
    STATUS       current
    DESCRIPTION
        "Cisco UCS sw:EthLanBorder:rn managed object property"
    ::= { cucsSwEthLanBorderEntry 3 }

cucsSwEthLanBorderFsmDescr OBJECT-TYPE
    SYNTAX       SnmpAdminString
    MAX-ACCESS   read-only
    STATUS       current
    DESCRIPTION
        "Cisco UCS sw:EthLanBorder:fsmDescr managed object property"
    ::= { cucsSwEthLanBorderEntry 4 }

cucsSwEthLanBorderFsmPrev OBJECT-TYPE
    SYNTAX       SnmpAdminString
    MAX-ACCESS   read-only
    STATUS       current
    DESCRIPTION
        "Cisco UCS sw:EthLanBorder:fsmPrev managed object property"
    ::= { cucsSwEthLanBorderEntry 5 }

cucsSwEthLanBorderFsmProgr OBJECT-TYPE
    SYNTAX       Gauge32
    MAX-ACCESS   read-only
    STATUS       current
    DESCRIPTION
        "Cisco UCS sw:EthLanBorder:fsmProgr managed object property"
    ::= { cucsSwEthLanBorderEntry 6 }

cucsSwEthLanBorderFsmRmtInvErrCode OBJECT-TYPE
    SYNTAX       Gauge32
    MAX-ACCESS   read-only
    STATUS       current
    DESCRIPTION
        "Cisco UCS sw:EthLanBorder:fsmRmtInvErrCode managed
        object property"
    ::= { cucsSwEthLanBorderEntry 7 }

cucsSwEthLanBorderFsmRmtInvErrDescr OBJECT-TYPE
    SYNTAX       SnmpAdminString
    MAX-ACCESS   read-only
    STATUS       current
    DESCRIPTION
        "Cisco UCS sw:EthLanBorder:fsmRmtInvErrDescr managed
        object property"
    ::= { cucsSwEthLanBorderEntry 8 }

cucsSwEthLanBorderFsmRmtInvRslt OBJECT-TYPE
    SYNTAX       CucsConditionRemoteInvRslt
    MAX-ACCESS   read-only
    STATUS       current
    DESCRIPTION
        "Cisco UCS sw:EthLanBorder:fsmRmtInvRslt managed object property"
    ::= { cucsSwEthLanBorderEntry 9 }

cucsSwEthLanBorderFsmStageDescr OBJECT-TYPE
    SYNTAX       SnmpAdminString
    MAX-ACCESS   read-only
    STATUS       current
    DESCRIPTION
        "Cisco UCS sw:EthLanBorder:fsmStageDescr managed object property"
    ::= { cucsSwEthLanBorderEntry 10 }

cucsSwEthLanBorderFsmStamp OBJECT-TYPE
    SYNTAX       DateAndTime
    MAX-ACCESS   read-only
    STATUS       current
    DESCRIPTION
        "Cisco UCS sw:EthLanBorder:fsmStamp managed object property"
    ::= { cucsSwEthLanBorderEntry 11 }

cucsSwEthLanBorderFsmStatus OBJECT-TYPE
    SYNTAX       SnmpAdminString
    MAX-ACCESS   read-only
    STATUS       current
    DESCRIPTION
        "Cisco UCS sw:EthLanBorder:fsmStatus managed object property"
    ::= { cucsSwEthLanBorderEntry 12 }

cucsSwEthLanBorderFsmTry OBJECT-TYPE
    SYNTAX       Gauge32
    MAX-ACCESS   read-only
    STATUS       current
    DESCRIPTION
        "Cisco UCS sw:EthLanBorder:fsmTry managed object property"
    ::= { cucsSwEthLanBorderEntry 13 }

cucsSwEthLanBorderLocale OBJECT-TYPE
    SYNTAX       CucsSwBorderDomainLocale
    MAX-ACCESS   read-only
    STATUS       current
    DESCRIPTION
        "Cisco UCS sw:EthLanBorder:locale managed object property"
    ::= { cucsSwEthLanBorderEntry 14 }

cucsSwEthLanBorderName OBJECT-TYPE
    SYNTAX       SnmpAdminString
    MAX-ACCESS   read-only
    STATUS       current
    DESCRIPTION
        "Cisco UCS sw:EthLanBorder:name managed object property"
    ::= { cucsSwEthLanBorderEntry 15 }

cucsSwEthLanBorderSwitchId OBJECT-TYPE
    SYNTAX       CucsNetworkSwitchId
    MAX-ACCESS   read-only
    STATUS       current
    DESCRIPTION
        "Cisco UCS sw:EthLanBorder:switchId managed object property"
    ::= { cucsSwEthLanBorderEntry 16 }

cucsSwEthLanBorderTransport OBJECT-TYPE
    SYNTAX       CucsSwEthLanBorderTransport
    MAX-ACCESS   read-only
    STATUS       current
    DESCRIPTION
        "Cisco UCS sw:EthLanBorder:transport managed object property"
    ::= { cucsSwEthLanBorderEntry 17 }

cucsSwEthLanBorderType OBJECT-TYPE
    SYNTAX       CucsSwLanBorderType
    MAX-ACCESS   read-only
    STATUS       current
    DESCRIPTION
        "Cisco UCS sw:EthLanBorder:type managed object property"
    ::= { cucsSwEthLanBorderEntry 18 }

cucsSwEthLanBorderFsmTaskTable OBJECT-TYPE
    SYNTAX           SEQUENCE OF CucsSwEthLanBorderFsmTaskEntry
    MAX-ACCESS       not-accessible
    STATUS           current
    DESCRIPTION
        "Cisco UCS sw:EthLanBorderFsmTask managed object table"
    ::= { cucsSwObjects 8 }

cucsSwEthLanBorderFsmTaskEntry OBJECT-TYPE
    SYNTAX           CucsSwEthLanBorderFsmTaskEntry
    MAX-ACCESS       not-accessible
    STATUS           current
    DESCRIPTION
        "Entry for the cucsSwEthLanBorderFsmTaskTable table."
    INDEX { cucsSwEthLanBorderFsmTaskInstanceId }
    ::= { cucsSwEthLanBorderFsmTaskTable 1 }

CucsSwEthLanBorderFsmTaskEntry ::= SEQUENCE {
    cucsSwEthLanBorderFsmTaskInstanceId                              CucsManagedObjectId,
    cucsSwEthLanBorderFsmTaskDn                                      CucsManagedObjectDn,
    cucsSwEthLanBorderFsmTaskRn                                      SnmpAdminString,
    cucsSwEthLanBorderFsmTaskCompletion                              CucsFsmCompletion,
    cucsSwEthLanBorderFsmTaskFlags                                   CucsFsmFlags,
    cucsSwEthLanBorderFsmTaskItem                                    CucsSwEthLanBorderFsmTaskItem,
    cucsSwEthLanBorderFsmTaskSeqId                                   Gauge32
}

cucsSwEthLanBorderFsmTaskInstanceId OBJECT-TYPE
    SYNTAX       CucsManagedObjectId
    MAX-ACCESS   not-accessible
    STATUS       current
    DESCRIPTION
        "Instance identifier of the managed object."
    ::= { cucsSwEthLanBorderFsmTaskEntry 1 }

cucsSwEthLanBorderFsmTaskDn OBJECT-TYPE
    SYNTAX       CucsManagedObjectDn
    MAX-ACCESS   read-only
    STATUS       current
    DESCRIPTION
        "Cisco UCS sw:EthLanBorderFsmTask:dn managed object property"
    ::= { cucsSwEthLanBorderFsmTaskEntry 2 }

cucsSwEthLanBorderFsmTaskRn OBJECT-TYPE
    SYNTAX       SnmpAdminString
    MAX-ACCESS   read-only
    STATUS       current
    DESCRIPTION
        "Cisco UCS sw:EthLanBorderFsmTask:rn managed object property"
    ::= { cucsSwEthLanBorderFsmTaskEntry 3 }

cucsSwEthLanBorderFsmTaskCompletion OBJECT-TYPE
    SYNTAX       CucsFsmCompletion
    MAX-ACCESS   read-only
    STATUS       current
    DESCRIPTION
        "Cisco UCS sw:EthLanBorderFsmTask:completion managed
        object property"
    ::= { cucsSwEthLanBorderFsmTaskEntry 4 }

cucsSwEthLanBorderFsmTaskFlags OBJECT-TYPE
    SYNTAX       CucsFsmFlags
    MAX-ACCESS   read-only
    STATUS       current
    DESCRIPTION
        "Cisco UCS sw:EthLanBorderFsmTask:flags managed object property"
    ::= { cucsSwEthLanBorderFsmTaskEntry 5 }

cucsSwEthLanBorderFsmTaskItem OBJECT-TYPE
    SYNTAX       CucsSwEthLanBorderFsmTaskItem
    MAX-ACCESS   read-only
    STATUS       current
    DESCRIPTION
        "Cisco UCS sw:EthLanBorderFsmTask:item managed object property"
    ::= { cucsSwEthLanBorderFsmTaskEntry 6 }

cucsSwEthLanBorderFsmTaskSeqId OBJECT-TYPE
    SYNTAX       Gauge32
    MAX-ACCESS   read-only
    STATUS       current
    DESCRIPTION
        "Cisco UCS sw:EthLanBorderFsmTask:seqId managed object property"
    ::= { cucsSwEthLanBorderFsmTaskEntry 7 }

cucsSwEthLanEpTable OBJECT-TYPE
    SYNTAX           SEQUENCE OF CucsSwEthLanEpEntry
    MAX-ACCESS       not-accessible
    STATUS           current
    DESCRIPTION
        "Cisco UCS sw:EthLanEp managed object table"
    ::= { cucsSwObjects 9 }

cucsSwEthLanEpEntry OBJECT-TYPE
    SYNTAX           CucsSwEthLanEpEntry
    MAX-ACCESS       not-accessible
    STATUS           current
    DESCRIPTION
        "Entry for the cucsSwEthLanEpTable table."
    INDEX { cucsSwEthLanEpInstanceId }
    ::= { cucsSwEthLanEpTable 1 }

CucsSwEthLanEpEntry ::= SEQUENCE {
    cucsSwEthLanEpInstanceId                                         CucsManagedObjectId,
    cucsSwEthLanEpDn                                                 CucsManagedObjectDn,
    cucsSwEthLanEpRn                                                 SnmpAdminString,
    cucsSwEthLanEpAdminSpeed                                         CucsPortEthSpeed,
    cucsSwEthLanEpAdminState                                         CucsFabricAdminState,
    cucsSwEthLanEpChassisId                                          Gauge32,
    cucsSwEthLanEpEpDn                                               SnmpAdminString,
    cucsSwEthLanEpIfRole                                             CucsSwLanEpIfRole,
    cucsSwEthLanEpIfType                                             CucsSwPIoEpIfType,
    cucsSwEthLanEpLocale                                             CucsSwBorderEpLocale,
    cucsSwEthLanEpName                                               SnmpAdminString,
    cucsSwEthLanEpPcId                                               Gauge32,
    cucsSwEthLanEpPeerDn                                             SnmpAdminString,
    cucsSwEthLanEpPeerPortId                                         Gauge32,
    cucsSwEthLanEpPeerSlotId                                         Gauge32,
    cucsSwEthLanEpPortId                                             Gauge32,
    cucsSwEthLanEpPriorityFlowCtrl                                   CucsFlowctrlPriorityPause,
    cucsSwEthLanEpRecvFlowCtrl                                       CucsFlowctrlFlowControl,
    cucsSwEthLanEpSendFlowCtrl                                       CucsFlowctrlFlowControl,
    cucsSwEthLanEpSlotId                                             Gauge32,
    cucsSwEthLanEpSwitchId                                           CucsNetworkSwitchId,
    cucsSwEthLanEpTransport                                          CucsSwEthLanEpTransport,
    cucsSwEthLanEpType                                               CucsSwLanEpType,
    cucsSwEthLanEpPeerChassisId                                      Gauge32,
    cucsSwEthLanEpLc                                                 CucsSwPIoEpLc
}

cucsSwEthLanEpInstanceId OBJECT-TYPE
    SYNTAX       CucsManagedObjectId
    MAX-ACCESS   not-accessible
    STATUS       current
    DESCRIPTION
        "Instance identifier of the managed object."
    ::= { cucsSwEthLanEpEntry 1 }

cucsSwEthLanEpDn OBJECT-TYPE
    SYNTAX       CucsManagedObjectDn
    MAX-ACCESS   read-only
    STATUS       current
    DESCRIPTION
        "Cisco UCS sw:EthLanEp:dn managed object property"
    ::= { cucsSwEthLanEpEntry 2 }

cucsSwEthLanEpRn OBJECT-TYPE
    SYNTAX       SnmpAdminString
    MAX-ACCESS   read-only
    STATUS       current
    DESCRIPTION
        "Cisco UCS sw:EthLanEp:rn managed object property"
    ::= { cucsSwEthLanEpEntry 3 }

cucsSwEthLanEpAdminSpeed OBJECT-TYPE
    SYNTAX       CucsPortEthSpeed
    MAX-ACCESS   read-only
    STATUS       current
    DESCRIPTION
        "Cisco UCS sw:EthLanEp:adminSpeed managed object property"
    ::= { cucsSwEthLanEpEntry 4 }

cucsSwEthLanEpAdminState OBJECT-TYPE
    SYNTAX       CucsFabricAdminState
    MAX-ACCESS   read-only
    STATUS       current
    DESCRIPTION
        "Cisco UCS sw:EthLanEp:adminState managed object property"
    ::= { cucsSwEthLanEpEntry 5 }

cucsSwEthLanEpChassisId OBJECT-TYPE
    SYNTAX       Gauge32
    MAX-ACCESS   read-only
    STATUS       current
    DESCRIPTION
        "Cisco UCS sw:EthLanEp:chassisId managed object property"
    ::= { cucsSwEthLanEpEntry 6 }

cucsSwEthLanEpEpDn OBJECT-TYPE
    SYNTAX       SnmpAdminString
    MAX-ACCESS   read-only
    STATUS       current
    DESCRIPTION
        "Cisco UCS sw:EthLanEp:epDn managed object property"
    ::= { cucsSwEthLanEpEntry 7 }

cucsSwEthLanEpIfRole OBJECT-TYPE
    SYNTAX       CucsSwLanEpIfRole
    MAX-ACCESS   read-only
    STATUS       current
    DESCRIPTION
        "Cisco UCS sw:EthLanEp:ifRole managed object property"
    ::= { cucsSwEthLanEpEntry 8 }

cucsSwEthLanEpIfType OBJECT-TYPE
    SYNTAX       CucsSwPIoEpIfType
    MAX-ACCESS   read-only
    STATUS       current
    DESCRIPTION
        "Cisco UCS sw:EthLanEp:ifType managed object property"
    ::= { cucsSwEthLanEpEntry 9 }

cucsSwEthLanEpLocale OBJECT-TYPE
    SYNTAX       CucsSwBorderEpLocale
    MAX-ACCESS   read-only
    STATUS       current
    DESCRIPTION
        "Cisco UCS sw:EthLanEp:locale managed object property"
    ::= { cucsSwEthLanEpEntry 10 }

cucsSwEthLanEpName OBJECT-TYPE
    SYNTAX       SnmpAdminString
    MAX-ACCESS   read-only
    STATUS       current
    DESCRIPTION
        "Cisco UCS sw:EthLanEp:name managed object property"
    ::= { cucsSwEthLanEpEntry 11 }

cucsSwEthLanEpPcId OBJECT-TYPE
    SYNTAX       Gauge32
    MAX-ACCESS   read-only
    STATUS       current
    DESCRIPTION
        "Cisco UCS sw:EthLanEp:pcId managed object property"
    ::= { cucsSwEthLanEpEntry 12 }

cucsSwEthLanEpPeerDn OBJECT-TYPE
    SYNTAX       SnmpAdminString
    MAX-ACCESS   read-only
    STATUS       current
    DESCRIPTION
        "Cisco UCS sw:EthLanEp:peerDn managed object property"
    ::= { cucsSwEthLanEpEntry 13 }

cucsSwEthLanEpPeerPortId OBJECT-TYPE
    SYNTAX       Gauge32
    MAX-ACCESS   read-only
    STATUS       current
    DESCRIPTION
        "Cisco UCS sw:EthLanEp:peerPortId managed object property"
    ::= { cucsSwEthLanEpEntry 14 }

cucsSwEthLanEpPeerSlotId OBJECT-TYPE
    SYNTAX       Gauge32
    MAX-ACCESS   read-only
    STATUS       current
    DESCRIPTION
        "Cisco UCS sw:EthLanEp:peerSlotId managed object property"
    ::= { cucsSwEthLanEpEntry 15 }

cucsSwEthLanEpPortId OBJECT-TYPE
    SYNTAX       Gauge32
    MAX-ACCESS   read-only
    STATUS       current
    DESCRIPTION
        "Cisco UCS sw:EthLanEp:portId managed object property"
    ::= { cucsSwEthLanEpEntry 16 }

cucsSwEthLanEpPriorityFlowCtrl OBJECT-TYPE
    SYNTAX       CucsFlowctrlPriorityPause
    MAX-ACCESS   read-only
    STATUS       current
    DESCRIPTION
        "Cisco UCS sw:EthLanEp:priorityFlowCtrl managed object property"
    ::= { cucsSwEthLanEpEntry 17 }

cucsSwEthLanEpRecvFlowCtrl OBJECT-TYPE
    SYNTAX       CucsFlowctrlFlowControl
    MAX-ACCESS   read-only
    STATUS       current
    DESCRIPTION
        "Cisco UCS sw:EthLanEp:recvFlowCtrl managed object property"
    ::= { cucsSwEthLanEpEntry 18 }

cucsSwEthLanEpSendFlowCtrl OBJECT-TYPE
    SYNTAX       CucsFlowctrlFlowControl
    MAX-ACCESS   read-only
    STATUS       current
    DESCRIPTION
        "Cisco UCS sw:EthLanEp:sendFlowCtrl managed object property"
    ::= { cucsSwEthLanEpEntry 19 }

cucsSwEthLanEpSlotId OBJECT-TYPE
    SYNTAX       Gauge32
    MAX-ACCESS   read-only
    STATUS       current
    DESCRIPTION
        "Cisco UCS sw:EthLanEp:slotId managed object property"
    ::= { cucsSwEthLanEpEntry 20 }

cucsSwEthLanEpSwitchId OBJECT-TYPE
    SYNTAX       CucsNetworkSwitchId
    MAX-ACCESS   read-only
    STATUS       current
    DESCRIPTION
        "Cisco UCS sw:EthLanEp:switchId managed object property"
    ::= { cucsSwEthLanEpEntry 21 }

cucsSwEthLanEpTransport OBJECT-TYPE
    SYNTAX       CucsSwEthLanEpTransport
    MAX-ACCESS   read-only
    STATUS       current
    DESCRIPTION
        "Cisco UCS sw:EthLanEp:transport managed object property"
    ::= { cucsSwEthLanEpEntry 22 }

cucsSwEthLanEpType OBJECT-TYPE
    SYNTAX       CucsSwLanEpType
    MAX-ACCESS   read-only
    STATUS       current
    DESCRIPTION
        "Cisco UCS sw:EthLanEp:type managed object property"
    ::= { cucsSwEthLanEpEntry 23 }

cucsSwEthLanEpPeerChassisId OBJECT-TYPE
    SYNTAX       Gauge32
    MAX-ACCESS   read-only
    STATUS       current
    DESCRIPTION
        "Cisco UCS sw:EthLanEp:peerChassisId managed object property"
    ::= { cucsSwEthLanEpEntry 24 }

cucsSwEthLanEpLc OBJECT-TYPE
    SYNTAX       CucsSwPIoEpLc
    MAX-ACCESS   read-only
    STATUS       current
    DESCRIPTION
        "Cisco UCS sw:EthLanEp:lc managed object property"
    ::= { cucsSwEthLanEpEntry 25 }

cucsSwEthLanMonTable OBJECT-TYPE
    SYNTAX           SEQUENCE OF CucsSwEthLanMonEntry
    MAX-ACCESS       not-accessible
    STATUS           current
    DESCRIPTION
        "Cisco UCS sw:EthLanMon managed object table"
    ::= { cucsSwObjects 10 }

cucsSwEthLanMonEntry OBJECT-TYPE
    SYNTAX           CucsSwEthLanMonEntry
    MAX-ACCESS       not-accessible
    STATUS           current
    DESCRIPTION
        "Entry for the cucsSwEthLanMonTable table."
    INDEX { cucsSwEthLanMonInstanceId }
    ::= { cucsSwEthLanMonTable 1 }

CucsSwEthLanMonEntry ::= SEQUENCE {
    cucsSwEthLanMonInstanceId                                        CucsManagedObjectId,
    cucsSwEthLanMonDn                                                CucsManagedObjectDn,
    cucsSwEthLanMonRn                                                SnmpAdminString,
    cucsSwEthLanMonLocale                                            CucsSwMonDomainLocale,
    cucsSwEthLanMonName                                              SnmpAdminString,
    cucsSwEthLanMonSwitchId                                          CucsNetworkSwitchId,
    cucsSwEthLanMonTransport                                         CucsSwEthLanMonTransport,
    cucsSwEthLanMonType                                              CucsSwLanMonType
}

cucsSwEthLanMonInstanceId OBJECT-TYPE
    SYNTAX       CucsManagedObjectId
    MAX-ACCESS   not-accessible
    STATUS       current
    DESCRIPTION
        "Instance identifier of the managed object."
    ::= { cucsSwEthLanMonEntry 1 }

cucsSwEthLanMonDn OBJECT-TYPE
    SYNTAX       CucsManagedObjectDn
    MAX-ACCESS   read-only
    STATUS       current
    DESCRIPTION
        "Cisco UCS sw:EthLanMon:dn managed object property"
    ::= { cucsSwEthLanMonEntry 2 }

cucsSwEthLanMonRn OBJECT-TYPE
    SYNTAX       SnmpAdminString
    MAX-ACCESS   read-only
    STATUS       current
    DESCRIPTION
        "Cisco UCS sw:EthLanMon:rn managed object property"
    ::= { cucsSwEthLanMonEntry 3 }

cucsSwEthLanMonLocale OBJECT-TYPE
    SYNTAX       CucsSwMonDomainLocale
    MAX-ACCESS   read-only
    STATUS       current
    DESCRIPTION
        "Cisco UCS sw:EthLanMon:locale managed object property"
    ::= { cucsSwEthLanMonEntry 4 }

cucsSwEthLanMonName OBJECT-TYPE
    SYNTAX       SnmpAdminString
    MAX-ACCESS   read-only
    STATUS       current
    DESCRIPTION
        "Cisco UCS sw:EthLanMon:name managed object property"
    ::= { cucsSwEthLanMonEntry 5 }

cucsSwEthLanMonSwitchId OBJECT-TYPE
    SYNTAX       CucsNetworkSwitchId
    MAX-ACCESS   read-only
    STATUS       current
    DESCRIPTION
        "Cisco UCS sw:EthLanMon:switchId managed object property"
    ::= { cucsSwEthLanMonEntry 6 }

cucsSwEthLanMonTransport OBJECT-TYPE
    SYNTAX       CucsSwEthLanMonTransport
    MAX-ACCESS   read-only
    STATUS       current
    DESCRIPTION
        "Cisco UCS sw:EthLanMon:transport managed object property"
    ::= { cucsSwEthLanMonEntry 7 }

cucsSwEthLanMonType OBJECT-TYPE
    SYNTAX       CucsSwLanMonType
    MAX-ACCESS   read-only
    STATUS       current
    DESCRIPTION
        "Cisco UCS sw:EthLanMon:type managed object property"
    ::= { cucsSwEthLanMonEntry 8 }

cucsSwEthLanPcTable OBJECT-TYPE
    SYNTAX           SEQUENCE OF CucsSwEthLanPcEntry
    MAX-ACCESS       not-accessible
    STATUS           current
    DESCRIPTION
        "Cisco UCS sw:EthLanPc managed object table"
    ::= { cucsSwObjects 11 }

cucsSwEthLanPcEntry OBJECT-TYPE
    SYNTAX           CucsSwEthLanPcEntry
    MAX-ACCESS       not-accessible
    STATUS           current
    DESCRIPTION
        "Entry for the cucsSwEthLanPcTable table."
    INDEX { cucsSwEthLanPcInstanceId }
    ::= { cucsSwEthLanPcTable 1 }

CucsSwEthLanPcEntry ::= SEQUENCE {
    cucsSwEthLanPcInstanceId                                         CucsManagedObjectId,
    cucsSwEthLanPcDn                                                 CucsManagedObjectDn,
    cucsSwEthLanPcRn                                                 SnmpAdminString,
    cucsSwEthLanPcAdminSpeed                                         CucsPortEthSpeed,
    cucsSwEthLanPcAdminState                                         CucsFabricAdminState,
    cucsSwEthLanPcEpDn                                               SnmpAdminString,
    cucsSwEthLanPcIfRole                                             CucsSwLanPcIfRole,
    cucsSwEthLanPcIfType                                             CucsSwCIoEpIfType,
    cucsSwEthLanPcLocale                                             CucsSwBorderPcLocale,
    cucsSwEthLanPcName                                               SnmpAdminString,
    cucsSwEthLanPcPeerDn                                             SnmpAdminString,
    cucsSwEthLanPcPortId                                             Gauge32,
    cucsSwEthLanPcPriorityFlowCtrl                                   CucsFlowctrlPriorityPause,
    cucsSwEthLanPcRecvFlowCtrl                                       CucsFlowctrlFlowControl,
    cucsSwEthLanPcSendFlowCtrl                                       CucsFlowctrlFlowControl,
    cucsSwEthLanPcSwitchId                                           CucsNetworkSwitchId,
    cucsSwEthLanPcTransport                                          CucsSwEthLanPcTransport,
    cucsSwEthLanPcType                                               CucsSwLanPcType,
    cucsSwEthLanPcMonTrafDir                                         CucsFabricTrafficDirection
}

cucsSwEthLanPcInstanceId OBJECT-TYPE
    SYNTAX       CucsManagedObjectId
    MAX-ACCESS   not-accessible
    STATUS       current
    DESCRIPTION
        "Instance identifier of the managed object."
    ::= { cucsSwEthLanPcEntry 1 }

cucsSwEthLanPcDn OBJECT-TYPE
    SYNTAX       CucsManagedObjectDn
    MAX-ACCESS   read-only
    STATUS       current
    DESCRIPTION
        "Cisco UCS sw:EthLanPc:dn managed object property"
    ::= { cucsSwEthLanPcEntry 2 }

cucsSwEthLanPcRn OBJECT-TYPE
    SYNTAX       SnmpAdminString
    MAX-ACCESS   read-only
    STATUS       current
    DESCRIPTION
        "Cisco UCS sw:EthLanPc:rn managed object property"
    ::= { cucsSwEthLanPcEntry 3 }

cucsSwEthLanPcAdminSpeed OBJECT-TYPE
    SYNTAX       CucsPortEthSpeed
    MAX-ACCESS   read-only
    STATUS       current
    DESCRIPTION
        "Cisco UCS sw:EthLanPc:adminSpeed managed object property"
    ::= { cucsSwEthLanPcEntry 4 }

cucsSwEthLanPcAdminState OBJECT-TYPE
    SYNTAX       CucsFabricAdminState
    MAX-ACCESS   read-only
    STATUS       current
    DESCRIPTION
        "Cisco UCS sw:EthLanPc:adminState managed object property"
    ::= { cucsSwEthLanPcEntry 5 }

cucsSwEthLanPcEpDn OBJECT-TYPE
    SYNTAX       SnmpAdminString
    MAX-ACCESS   read-only
    STATUS       current
    DESCRIPTION
        "Cisco UCS sw:EthLanPc:epDn managed object property"
    ::= { cucsSwEthLanPcEntry 6 }

cucsSwEthLanPcIfRole OBJECT-TYPE
    SYNTAX       CucsSwLanPcIfRole
    MAX-ACCESS   read-only
    STATUS       current
    DESCRIPTION
        "Cisco UCS sw:EthLanPc:ifRole managed object property"
    ::= { cucsSwEthLanPcEntry 7 }

cucsSwEthLanPcIfType OBJECT-TYPE
    SYNTAX       CucsSwCIoEpIfType
    MAX-ACCESS   read-only
    STATUS       current
    DESCRIPTION
        "Cisco UCS sw:EthLanPc:ifType managed object property"
    ::= { cucsSwEthLanPcEntry 8 }

cucsSwEthLanPcLocale OBJECT-TYPE
    SYNTAX       CucsSwBorderPcLocale
    MAX-ACCESS   read-only
    STATUS       current
    DESCRIPTION
        "Cisco UCS sw:EthLanPc:locale managed object property"
    ::= { cucsSwEthLanPcEntry 9 }

cucsSwEthLanPcName OBJECT-TYPE
    SYNTAX       SnmpAdminString
    MAX-ACCESS   read-only
    STATUS       current
    DESCRIPTION
        "Cisco UCS sw:EthLanPc:name managed object property"
    ::= { cucsSwEthLanPcEntry 10 }

cucsSwEthLanPcPeerDn OBJECT-TYPE
    SYNTAX       SnmpAdminString
    MAX-ACCESS   read-only
    STATUS       current
    DESCRIPTION
        "Cisco UCS sw:EthLanPc:peerDn managed object property"
    ::= { cucsSwEthLanPcEntry 11 }

cucsSwEthLanPcPortId OBJECT-TYPE
    SYNTAX       Gauge32
    MAX-ACCESS   read-only
    STATUS       current
    DESCRIPTION
        "Cisco UCS sw:EthLanPc:portId managed object property"
    ::= { cucsSwEthLanPcEntry 12 }

cucsSwEthLanPcPriorityFlowCtrl OBJECT-TYPE
    SYNTAX       CucsFlowctrlPriorityPause
    MAX-ACCESS   read-only
    STATUS       current
    DESCRIPTION
        "Cisco UCS sw:EthLanPc:priorityFlowCtrl managed object property"
    ::= { cucsSwEthLanPcEntry 13 }

cucsSwEthLanPcRecvFlowCtrl OBJECT-TYPE
    SYNTAX       CucsFlowctrlFlowControl
    MAX-ACCESS   read-only
    STATUS       current
    DESCRIPTION
        "Cisco UCS sw:EthLanPc:recvFlowCtrl managed object property"
    ::= { cucsSwEthLanPcEntry 14 }

cucsSwEthLanPcSendFlowCtrl OBJECT-TYPE
    SYNTAX       CucsFlowctrlFlowControl
    MAX-ACCESS   read-only
    STATUS       current
    DESCRIPTION
        "Cisco UCS sw:EthLanPc:sendFlowCtrl managed object property"
    ::= { cucsSwEthLanPcEntry 15 }

cucsSwEthLanPcSwitchId OBJECT-TYPE
    SYNTAX       CucsNetworkSwitchId
    MAX-ACCESS   read-only
    STATUS       current
    DESCRIPTION
        "Cisco UCS sw:EthLanPc:switchId managed object property"
    ::= { cucsSwEthLanPcEntry 16 }

cucsSwEthLanPcTransport OBJECT-TYPE
    SYNTAX       CucsSwEthLanPcTransport
    MAX-ACCESS   read-only
    STATUS       current
    DESCRIPTION
        "Cisco UCS sw:EthLanPc:transport managed object property"
    ::= { cucsSwEthLanPcEntry 17 }

cucsSwEthLanPcType OBJECT-TYPE
    SYNTAX       CucsSwLanPcType
    MAX-ACCESS   read-only
    STATUS       current
    DESCRIPTION
        "Cisco UCS sw:EthLanPc:type managed object property"
    ::= { cucsSwEthLanPcEntry 18 }

cucsSwEthLanPcMonTrafDir OBJECT-TYPE
    SYNTAX       CucsFabricTrafficDirection
    MAX-ACCESS   read-only
    STATUS       current
    DESCRIPTION
        "Cisco UCS sw:EthLanPc:monTrafDir managed object property"
    ::= { cucsSwEthLanPcEntry 19 }

cucsSwEthMonTable OBJECT-TYPE
    SYNTAX           SEQUENCE OF CucsSwEthMonEntry
    MAX-ACCESS       not-accessible
    STATUS           current
    DESCRIPTION
        "Cisco UCS sw:EthMon managed object table"
    ::= { cucsSwObjects 12 }

cucsSwEthMonEntry OBJECT-TYPE
    SYNTAX           CucsSwEthMonEntry
    MAX-ACCESS       not-accessible
    STATUS           current
    DESCRIPTION
        "Entry for the cucsSwEthMonTable table."
    INDEX { cucsSwEthMonInstanceId }
    ::= { cucsSwEthMonTable 1 }

CucsSwEthMonEntry ::= SEQUENCE {
    cucsSwEthMonInstanceId                                           CucsManagedObjectId,
    cucsSwEthMonDn                                                   CucsManagedObjectDn,
    cucsSwEthMonRn                                                   SnmpAdminString,
    cucsSwEthMonAdminState                                           CucsSwMonAdminState,
    cucsSwEthMonFsmDescr                                             SnmpAdminString,
    cucsSwEthMonFsmPrev                                              SnmpAdminString,
    cucsSwEthMonFsmProgr                                             Gauge32,
    cucsSwEthMonFsmRmtInvErrCode                                     Gauge32,
    cucsSwEthMonFsmRmtInvErrDescr                                    SnmpAdminString,
    cucsSwEthMonFsmRmtInvRslt                                        CucsConditionRemoteInvRslt,
    cucsSwEthMonFsmStageDescr                                        SnmpAdminString,
    cucsSwEthMonFsmStamp                                             DateAndTime,
    cucsSwEthMonFsmStatus                                            SnmpAdminString,
    cucsSwEthMonFsmTry                                               Gauge32,
    cucsSwEthMonLifeCycle                                            CucsSwMonLifeCycle,
    cucsSwEthMonName                                                 SnmpAdminString,
    cucsSwEthMonSession                                              Gauge32,
    cucsSwEthMonSwitchId                                             CucsNetworkSwitchId,
    cucsSwEthMonTransport                                            CucsSwEthMonTransport,
    cucsSwEthMonType                                                 CucsSwEthMonType,
    cucsSwEthMonHasLastDest                                          TruthValue,
    cucsSwEthMonPeerDn                                               SnmpAdminString
}

cucsSwEthMonInstanceId OBJECT-TYPE
    SYNTAX       CucsManagedObjectId
    MAX-ACCESS   not-accessible
    STATUS       current
    DESCRIPTION
        "Instance identifier of the managed object."
    ::= { cucsSwEthMonEntry 1 }

cucsSwEthMonDn OBJECT-TYPE
    SYNTAX       CucsManagedObjectDn
    MAX-ACCESS   read-only
    STATUS       current
    DESCRIPTION
        "Cisco UCS sw:EthMon:dn managed object property"
    ::= { cucsSwEthMonEntry 2 }

cucsSwEthMonRn OBJECT-TYPE
    SYNTAX       SnmpAdminString
    MAX-ACCESS   read-only
    STATUS       current
    DESCRIPTION
        "Cisco UCS sw:EthMon:rn managed object property"
    ::= { cucsSwEthMonEntry 3 }

cucsSwEthMonAdminState OBJECT-TYPE
    SYNTAX       CucsSwMonAdminState
    MAX-ACCESS   read-only
    STATUS       current
    DESCRIPTION
        "Cisco UCS sw:EthMon:adminState managed object property"
    ::= { cucsSwEthMonEntry 4 }

cucsSwEthMonFsmDescr OBJECT-TYPE
    SYNTAX       SnmpAdminString
    MAX-ACCESS   read-only
    STATUS       current
    DESCRIPTION
        "Cisco UCS sw:EthMon:fsmDescr managed object property"
    ::= { cucsSwEthMonEntry 5 }

cucsSwEthMonFsmPrev OBJECT-TYPE
    SYNTAX       SnmpAdminString
    MAX-ACCESS   read-only
    STATUS       current
    DESCRIPTION
        "Cisco UCS sw:EthMon:fsmPrev managed object property"
    ::= { cucsSwEthMonEntry 6 }

cucsSwEthMonFsmProgr OBJECT-TYPE
    SYNTAX       Gauge32
    MAX-ACCESS   read-only
    STATUS       current
    DESCRIPTION
        "Cisco UCS sw:EthMon:fsmProgr managed object property"
    ::= { cucsSwEthMonEntry 7 }

cucsSwEthMonFsmRmtInvErrCode OBJECT-TYPE
    SYNTAX       Gauge32
    MAX-ACCESS   read-only
    STATUS       current
    DESCRIPTION
        "Cisco UCS sw:EthMon:fsmRmtInvErrCode managed object property"
    ::= { cucsSwEthMonEntry 8 }

cucsSwEthMonFsmRmtInvErrDescr OBJECT-TYPE
    SYNTAX       SnmpAdminString
    MAX-ACCESS   read-only
    STATUS       current
    DESCRIPTION
        "Cisco UCS sw:EthMon:fsmRmtInvErrDescr managed object property"
    ::= { cucsSwEthMonEntry 9 }

cucsSwEthMonFsmRmtInvRslt OBJECT-TYPE
    SYNTAX       CucsConditionRemoteInvRslt
    MAX-ACCESS   read-only
    STATUS       current
    DESCRIPTION
        "Cisco UCS sw:EthMon:fsmRmtInvRslt managed object property"
    ::= { cucsSwEthMonEntry 10 }

cucsSwEthMonFsmStageDescr OBJECT-TYPE
    SYNTAX       SnmpAdminString
    MAX-ACCESS   read-only
    STATUS       current
    DESCRIPTION
        "Cisco UCS sw:EthMon:fsmStageDescr managed object property"
    ::= { cucsSwEthMonEntry 11 }

cucsSwEthMonFsmStamp OBJECT-TYPE
    SYNTAX       DateAndTime
    MAX-ACCESS   read-only
    STATUS       current
    DESCRIPTION
        "Cisco UCS sw:EthMon:fsmStamp managed object property"
    ::= { cucsSwEthMonEntry 12 }

cucsSwEthMonFsmStatus OBJECT-TYPE
    SYNTAX       SnmpAdminString
    MAX-ACCESS   read-only
    STATUS       current
    DESCRIPTION
        "Cisco UCS sw:EthMon:fsmStatus managed object property"
    ::= { cucsSwEthMonEntry 13 }

cucsSwEthMonFsmTry OBJECT-TYPE
    SYNTAX       Gauge32
    MAX-ACCESS   read-only
    STATUS       current
    DESCRIPTION
        "Cisco UCS sw:EthMon:fsmTry managed object property"
    ::= { cucsSwEthMonEntry 14 }

cucsSwEthMonLifeCycle OBJECT-TYPE
    SYNTAX       CucsSwMonLifeCycle
    MAX-ACCESS   read-only
    STATUS       current
    DESCRIPTION
        "Cisco UCS sw:EthMon:lifeCycle managed object property"
    ::= { cucsSwEthMonEntry 15 }

cucsSwEthMonName OBJECT-TYPE
    SYNTAX       SnmpAdminString
    MAX-ACCESS   read-only
    STATUS       current
    DESCRIPTION
        "Cisco UCS sw:EthMon:name managed object property"
    ::= { cucsSwEthMonEntry 16 }

cucsSwEthMonSession OBJECT-TYPE
    SYNTAX       Gauge32
    MAX-ACCESS   read-only
    STATUS       current
    DESCRIPTION
        "Cisco UCS sw:EthMon:session managed object property"
    ::= { cucsSwEthMonEntry 17 }

cucsSwEthMonSwitchId OBJECT-TYPE
    SYNTAX       CucsNetworkSwitchId
    MAX-ACCESS   read-only
    STATUS       current
    DESCRIPTION
        "Cisco UCS sw:EthMon:switchId managed object property"
    ::= { cucsSwEthMonEntry 18 }

cucsSwEthMonTransport OBJECT-TYPE
    SYNTAX       CucsSwEthMonTransport
    MAX-ACCESS   read-only
    STATUS       current
    DESCRIPTION
        "Cisco UCS sw:EthMon:transport managed object property"
    ::= { cucsSwEthMonEntry 19 }

cucsSwEthMonType OBJECT-TYPE
    SYNTAX       CucsSwEthMonType
    MAX-ACCESS   read-only
    STATUS       current
    DESCRIPTION
        "Cisco UCS sw:EthMon:type managed object property"
    ::= { cucsSwEthMonEntry 20 }

cucsSwEthMonHasLastDest OBJECT-TYPE
    SYNTAX       TruthValue
    MAX-ACCESS   read-only
    STATUS       current
    DESCRIPTION
        "Cisco UCS sw:EthMon:hasLastDest managed object property"
    ::= { cucsSwEthMonEntry 21 }

cucsSwEthMonPeerDn OBJECT-TYPE
    SYNTAX       SnmpAdminString
    MAX-ACCESS   read-only
    STATUS       current
    DESCRIPTION
        "Cisco UCS sw:EthMon:peerDn managed object property"
    ::= { cucsSwEthMonEntry 22 }

cucsSwEthMonDestEpTable OBJECT-TYPE
    SYNTAX           SEQUENCE OF CucsSwEthMonDestEpEntry
    MAX-ACCESS       not-accessible
    STATUS           current
    DESCRIPTION
        "Cisco UCS sw:EthMonDestEp managed object table"
    ::= { cucsSwObjects 13 }

cucsSwEthMonDestEpEntry OBJECT-TYPE
    SYNTAX           CucsSwEthMonDestEpEntry
    MAX-ACCESS       not-accessible
    STATUS           current
    DESCRIPTION
        "Entry for the cucsSwEthMonDestEpTable table."
    INDEX { cucsSwEthMonDestEpInstanceId }
    ::= { cucsSwEthMonDestEpTable 1 }

CucsSwEthMonDestEpEntry ::= SEQUENCE {
    cucsSwEthMonDestEpInstanceId                                     CucsManagedObjectId,
    cucsSwEthMonDestEpDn                                             CucsManagedObjectDn,
    cucsSwEthMonDestEpRn                                             SnmpAdminString,
    cucsSwEthMonDestEpAdminState                                     CucsFabricAdminState,
    cucsSwEthMonDestEpChassisId                                      Gauge32,
    cucsSwEthMonDestEpEpDn                                           SnmpAdminString,
    cucsSwEthMonDestEpIfRole                                         CucsNetworkPortRole,
    cucsSwEthMonDestEpIfType                                         CucsSwPIoEpIfType,
    cucsSwEthMonDestEpLocale                                         CucsNetworkLocale,
    cucsSwEthMonDestEpName                                           SnmpAdminString,
    cucsSwEthMonDestEpPeerDn                                         SnmpAdminString,
    cucsSwEthMonDestEpPeerPortId                                     Gauge32,
    cucsSwEthMonDestEpPeerSlotId                                     Gauge32,
    cucsSwEthMonDestEpPortId                                         Gauge32,
    cucsSwEthMonDestEpSlotId                                         Gauge32,
    cucsSwEthMonDestEpSwitchId                                       CucsNetworkSwitchId,
    cucsSwEthMonDestEpTransport                                      CucsSwEthMonDestEpTransport,
    cucsSwEthMonDestEpType                                           CucsNetworkConnectionType,
    cucsSwEthMonDestEpPeerChassisId                                  Gauge32,
    cucsSwEthMonDestEpLc                                             CucsSwPIoEpLc
}

cucsSwEthMonDestEpInstanceId OBJECT-TYPE
    SYNTAX       CucsManagedObjectId
    MAX-ACCESS   not-accessible
    STATUS       current
    DESCRIPTION
        "Instance identifier of the managed object."
    ::= { cucsSwEthMonDestEpEntry 1 }

cucsSwEthMonDestEpDn OBJECT-TYPE
    SYNTAX       CucsManagedObjectDn
    MAX-ACCESS   read-only
    STATUS       current
    DESCRIPTION
        "Cisco UCS sw:EthMonDestEp:dn managed object property"
    ::= { cucsSwEthMonDestEpEntry 2 }

cucsSwEthMonDestEpRn OBJECT-TYPE
    SYNTAX       SnmpAdminString
    MAX-ACCESS   read-only
    STATUS       current
    DESCRIPTION
        "Cisco UCS sw:EthMonDestEp:rn managed object property"
    ::= { cucsSwEthMonDestEpEntry 3 }

cucsSwEthMonDestEpAdminState OBJECT-TYPE
    SYNTAX       CucsFabricAdminState
    MAX-ACCESS   read-only
    STATUS       current
    DESCRIPTION
        "Cisco UCS sw:EthMonDestEp:adminState managed object property"
    ::= { cucsSwEthMonDestEpEntry 4 }

cucsSwEthMonDestEpChassisId OBJECT-TYPE
    SYNTAX       Gauge32
    MAX-ACCESS   read-only
    STATUS       current
    DESCRIPTION
        "Cisco UCS sw:EthMonDestEp:chassisId managed object property"
    ::= { cucsSwEthMonDestEpEntry 5 }

cucsSwEthMonDestEpEpDn OBJECT-TYPE
    SYNTAX       SnmpAdminString
    MAX-ACCESS   read-only
    STATUS       current
    DESCRIPTION
        "Cisco UCS sw:EthMonDestEp:epDn managed object property"
    ::= { cucsSwEthMonDestEpEntry 6 }

cucsSwEthMonDestEpIfRole OBJECT-TYPE
    SYNTAX       CucsNetworkPortRole
    MAX-ACCESS   read-only
    STATUS       current
    DESCRIPTION
        "Cisco UCS sw:EthMonDestEp:ifRole managed object property"
    ::= { cucsSwEthMonDestEpEntry 7 }

cucsSwEthMonDestEpIfType OBJECT-TYPE
    SYNTAX       CucsSwPIoEpIfType
    MAX-ACCESS   read-only
    STATUS       current
    DESCRIPTION
        "Cisco UCS sw:EthMonDestEp:ifType managed object property"
    ::= { cucsSwEthMonDestEpEntry 8 }

cucsSwEthMonDestEpLocale OBJECT-TYPE
    SYNTAX       CucsNetworkLocale
    MAX-ACCESS   read-only
    STATUS       current
    DESCRIPTION
        "Cisco UCS sw:EthMonDestEp:locale managed object property"
    ::= { cucsSwEthMonDestEpEntry 9 }

cucsSwEthMonDestEpName OBJECT-TYPE
    SYNTAX       SnmpAdminString
    MAX-ACCESS   read-only
    STATUS       current
    DESCRIPTION
        "Cisco UCS sw:EthMonDestEp:name managed object property"
    ::= { cucsSwEthMonDestEpEntry 10 }

cucsSwEthMonDestEpPeerDn OBJECT-TYPE
    SYNTAX       SnmpAdminString
    MAX-ACCESS   read-only
    STATUS       current
    DESCRIPTION
        "Cisco UCS sw:EthMonDestEp:peerDn managed object property"
    ::= { cucsSwEthMonDestEpEntry 11 }

cucsSwEthMonDestEpPeerPortId OBJECT-TYPE
    SYNTAX       Gauge32
    MAX-ACCESS   read-only
    STATUS       current
    DESCRIPTION
        "Cisco UCS sw:EthMonDestEp:peerPortId managed object property"
    ::= { cucsSwEthMonDestEpEntry 12 }

cucsSwEthMonDestEpPeerSlotId OBJECT-TYPE
    SYNTAX       Gauge32
    MAX-ACCESS   read-only
    STATUS       current
    DESCRIPTION
        "Cisco UCS sw:EthMonDestEp:peerSlotId managed object property"
    ::= { cucsSwEthMonDestEpEntry 13 }

cucsSwEthMonDestEpPortId OBJECT-TYPE
    SYNTAX       Gauge32
    MAX-ACCESS   read-only
    STATUS       current
    DESCRIPTION
        "Cisco UCS sw:EthMonDestEp:portId managed object property"
    ::= { cucsSwEthMonDestEpEntry 14 }

cucsSwEthMonDestEpSlotId OBJECT-TYPE
    SYNTAX       Gauge32
    MAX-ACCESS   read-only
    STATUS       current
    DESCRIPTION
        "Cisco UCS sw:EthMonDestEp:slotId managed object property"
    ::= { cucsSwEthMonDestEpEntry 15 }

cucsSwEthMonDestEpSwitchId OBJECT-TYPE
    SYNTAX       CucsNetworkSwitchId
    MAX-ACCESS   read-only
    STATUS       current
    DESCRIPTION
        "Cisco UCS sw:EthMonDestEp:switchId managed object property"
    ::= { cucsSwEthMonDestEpEntry 16 }

cucsSwEthMonDestEpTransport OBJECT-TYPE
    SYNTAX       CucsSwEthMonDestEpTransport
    MAX-ACCESS   read-only
    STATUS       current
    DESCRIPTION
        "Cisco UCS sw:EthMonDestEp:transport managed object property"
    ::= { cucsSwEthMonDestEpEntry 17 }

cucsSwEthMonDestEpType OBJECT-TYPE
    SYNTAX       CucsNetworkConnectionType
    MAX-ACCESS   read-only
    STATUS       current
    DESCRIPTION
        "Cisco UCS sw:EthMonDestEp:type managed object property"
    ::= { cucsSwEthMonDestEpEntry 18 }

cucsSwEthMonDestEpPeerChassisId OBJECT-TYPE
    SYNTAX       Gauge32
    MAX-ACCESS   read-only
    STATUS       current
    DESCRIPTION
        "Cisco UCS sw:EthMonDestEp:peerChassisId managed object property"
    ::= { cucsSwEthMonDestEpEntry 19 }

cucsSwEthMonDestEpLc OBJECT-TYPE
    SYNTAX       CucsSwPIoEpLc
    MAX-ACCESS   read-only
    STATUS       current
    DESCRIPTION
        "Cisco UCS sw:EthMonDestEp:lc managed object property"
    ::= { cucsSwEthMonDestEpEntry 20 }

cucsSwEthMonFsmTaskTable OBJECT-TYPE
    SYNTAX           SEQUENCE OF CucsSwEthMonFsmTaskEntry
    MAX-ACCESS       not-accessible
    STATUS           current
    DESCRIPTION
        "Cisco UCS sw:EthMonFsmTask managed object table"
    ::= { cucsSwObjects 14 }

cucsSwEthMonFsmTaskEntry OBJECT-TYPE
    SYNTAX           CucsSwEthMonFsmTaskEntry
    MAX-ACCESS       not-accessible
    STATUS           current
    DESCRIPTION
        "Entry for the cucsSwEthMonFsmTaskTable table."
    INDEX { cucsSwEthMonFsmTaskInstanceId }
    ::= { cucsSwEthMonFsmTaskTable 1 }

CucsSwEthMonFsmTaskEntry ::= SEQUENCE {
    cucsSwEthMonFsmTaskInstanceId                                    CucsManagedObjectId,
    cucsSwEthMonFsmTaskDn                                            CucsManagedObjectDn,
    cucsSwEthMonFsmTaskRn                                            SnmpAdminString,
    cucsSwEthMonFsmTaskCompletion                                    CucsFsmCompletion,
    cucsSwEthMonFsmTaskFlags                                         CucsFsmFlags,
    cucsSwEthMonFsmTaskItem                                          CucsSwEthMonFsmTaskItem,
    cucsSwEthMonFsmTaskSeqId                                         Gauge32
}

cucsSwEthMonFsmTaskInstanceId OBJECT-TYPE
    SYNTAX       CucsManagedObjectId
    MAX-ACCESS   not-accessible
    STATUS       current
    DESCRIPTION
        "Instance identifier of the managed object."
    ::= { cucsSwEthMonFsmTaskEntry 1 }

cucsSwEthMonFsmTaskDn OBJECT-TYPE
    SYNTAX       CucsManagedObjectDn
    MAX-ACCESS   read-only
    STATUS       current
    DESCRIPTION
        "Cisco UCS sw:EthMonFsmTask:dn managed object property"
    ::= { cucsSwEthMonFsmTaskEntry 2 }

cucsSwEthMonFsmTaskRn OBJECT-TYPE
    SYNTAX       SnmpAdminString
    MAX-ACCESS   read-only
    STATUS       current
    DESCRIPTION
        "Cisco UCS sw:EthMonFsmTask:rn managed object property"
    ::= { cucsSwEthMonFsmTaskEntry 3 }

cucsSwEthMonFsmTaskCompletion OBJECT-TYPE
    SYNTAX       CucsFsmCompletion
    MAX-ACCESS   read-only
    STATUS       current
    DESCRIPTION
        "Cisco UCS sw:EthMonFsmTask:completion managed object property"
    ::= { cucsSwEthMonFsmTaskEntry 4 }

cucsSwEthMonFsmTaskFlags OBJECT-TYPE
    SYNTAX       CucsFsmFlags
    MAX-ACCESS   read-only
    STATUS       current
    DESCRIPTION
        "Cisco UCS sw:EthMonFsmTask:flags managed object property"
    ::= { cucsSwEthMonFsmTaskEntry 5 }

cucsSwEthMonFsmTaskItem OBJECT-TYPE
    SYNTAX       CucsSwEthMonFsmTaskItem
    MAX-ACCESS   read-only
    STATUS       current
    DESCRIPTION
        "Cisco UCS sw:EthMonFsmTask:item managed object property"
    ::= { cucsSwEthMonFsmTaskEntry 6 }

cucsSwEthMonFsmTaskSeqId OBJECT-TYPE
    SYNTAX       Gauge32
    MAX-ACCESS   read-only
    STATUS       current
    DESCRIPTION
        "Cisco UCS sw:EthMonFsmTask:seqId managed object property"
    ::= { cucsSwEthMonFsmTaskEntry 7 }

cucsSwEthMonSrcEpTable OBJECT-TYPE
    SYNTAX           SEQUENCE OF CucsSwEthMonSrcEpEntry
    MAX-ACCESS       not-accessible
    STATUS           current
    DESCRIPTION
        "Cisco UCS sw:EthMonSrcEp managed object table"
    ::= { cucsSwObjects 15 }

cucsSwEthMonSrcEpEntry OBJECT-TYPE
    SYNTAX           CucsSwEthMonSrcEpEntry
    MAX-ACCESS       not-accessible
    STATUS           current
    DESCRIPTION
        "Entry for the cucsSwEthMonSrcEpTable table."
    INDEX { cucsSwEthMonSrcEpInstanceId }
    ::= { cucsSwEthMonSrcEpTable 1 }

CucsSwEthMonSrcEpEntry ::= SEQUENCE {
    cucsSwEthMonSrcEpInstanceId                                      CucsManagedObjectId,
    cucsSwEthMonSrcEpDn                                              CucsManagedObjectDn,
    cucsSwEthMonSrcEpRn                                              SnmpAdminString,
    cucsSwEthMonSrcEpAdminState                                      CucsFabricAdminState,
    cucsSwEthMonSrcEpChassisId                                       Gauge32,
    cucsSwEthMonSrcEpEpDn                                            SnmpAdminString,
    cucsSwEthMonSrcEpIfRole                                          CucsNetworkPortRole,
    cucsSwEthMonSrcEpIfType                                          CucsSwPIoEpIfType,
    cucsSwEthMonSrcEpLocale                                          CucsSwMonSrcEpLocale,
    cucsSwEthMonSrcEpMonTrafDir                                      CucsFabricTrafficDirection,
    cucsSwEthMonSrcEpName                                            SnmpAdminString,
    cucsSwEthMonSrcEpPeerDn                                          SnmpAdminString,
    cucsSwEthMonSrcEpPeerPortId                                      Gauge32,
    cucsSwEthMonSrcEpPeerSlotId                                      Gauge32,
    cucsSwEthMonSrcEpPortId                                          Gauge32,
    cucsSwEthMonSrcEpSlotId                                          Gauge32,
    cucsSwEthMonSrcEpSwitchId                                        CucsNetworkSwitchId,
    cucsSwEthMonSrcEpTransport                                       CucsSwEthMonSrcEpTransport,
    cucsSwEthMonSrcEpType                                            CucsNetworkConnectionType,
    cucsSwEthMonSrcEpPeerChassisId                                   Gauge32,
    cucsSwEthMonSrcEpLc                                              CucsSwPIoEpLc
}

cucsSwEthMonSrcEpInstanceId OBJECT-TYPE
    SYNTAX       CucsManagedObjectId
    MAX-ACCESS   not-accessible
    STATUS       current
    DESCRIPTION
        "Instance identifier of the managed object."
    ::= { cucsSwEthMonSrcEpEntry 1 }

cucsSwEthMonSrcEpDn OBJECT-TYPE
    SYNTAX       CucsManagedObjectDn
    MAX-ACCESS   read-only
    STATUS       current
    DESCRIPTION
        "Cisco UCS sw:EthMonSrcEp:dn managed object property"
    ::= { cucsSwEthMonSrcEpEntry 2 }

cucsSwEthMonSrcEpRn OBJECT-TYPE
    SYNTAX       SnmpAdminString
    MAX-ACCESS   read-only
    STATUS       current
    DESCRIPTION
        "Cisco UCS sw:EthMonSrcEp:rn managed object property"
    ::= { cucsSwEthMonSrcEpEntry 3 }

cucsSwEthMonSrcEpAdminState OBJECT-TYPE
    SYNTAX       CucsFabricAdminState
    MAX-ACCESS   read-only
    STATUS       current
    DESCRIPTION
        "Cisco UCS sw:EthMonSrcEp:adminState managed object property"
    ::= { cucsSwEthMonSrcEpEntry 4 }

cucsSwEthMonSrcEpChassisId OBJECT-TYPE
    SYNTAX       Gauge32
    MAX-ACCESS   read-only
    STATUS       current
    DESCRIPTION
        "Cisco UCS sw:EthMonSrcEp:chassisId managed object property"
    ::= { cucsSwEthMonSrcEpEntry 5 }

cucsSwEthMonSrcEpEpDn OBJECT-TYPE
    SYNTAX       SnmpAdminString
    MAX-ACCESS   read-only
    STATUS       current
    DESCRIPTION
        "Cisco UCS sw:EthMonSrcEp:epDn managed object property"
    ::= { cucsSwEthMonSrcEpEntry 6 }

cucsSwEthMonSrcEpIfRole OBJECT-TYPE
    SYNTAX       CucsNetworkPortRole
    MAX-ACCESS   read-only
    STATUS       current
    DESCRIPTION
        "Cisco UCS sw:EthMonSrcEp:ifRole managed object property"
    ::= { cucsSwEthMonSrcEpEntry 7 }

cucsSwEthMonSrcEpIfType OBJECT-TYPE
    SYNTAX       CucsSwPIoEpIfType
    MAX-ACCESS   read-only
    STATUS       current
    DESCRIPTION
        "Cisco UCS sw:EthMonSrcEp:ifType managed object property"
    ::= { cucsSwEthMonSrcEpEntry 8 }

cucsSwEthMonSrcEpLocale OBJECT-TYPE
    SYNTAX       CucsSwMonSrcEpLocale
    MAX-ACCESS   read-only
    STATUS       current
    DESCRIPTION
        "Cisco UCS sw:EthMonSrcEp:locale managed object property"
    ::= { cucsSwEthMonSrcEpEntry 9 }

cucsSwEthMonSrcEpMonTrafDir OBJECT-TYPE
    SYNTAX       CucsFabricTrafficDirection
    MAX-ACCESS   read-only
    STATUS       current
    DESCRIPTION
        "Cisco UCS sw:EthMonSrcEp:monTrafDir managed object property"
    ::= { cucsSwEthMonSrcEpEntry 10 }

cucsSwEthMonSrcEpName OBJECT-TYPE
    SYNTAX       SnmpAdminString
    MAX-ACCESS   read-only
    STATUS       current
    DESCRIPTION
        "Cisco UCS sw:EthMonSrcEp:name managed object property"
    ::= { cucsSwEthMonSrcEpEntry 11 }

cucsSwEthMonSrcEpPeerDn OBJECT-TYPE
    SYNTAX       SnmpAdminString
    MAX-ACCESS   read-only
    STATUS       current
    DESCRIPTION
        "Cisco UCS sw:EthMonSrcEp:peerDn managed object property"
    ::= { cucsSwEthMonSrcEpEntry 12 }

cucsSwEthMonSrcEpPeerPortId OBJECT-TYPE
    SYNTAX       Gauge32
    MAX-ACCESS   read-only
    STATUS       current
    DESCRIPTION
        "Cisco UCS sw:EthMonSrcEp:peerPortId managed object property"
    ::= { cucsSwEthMonSrcEpEntry 13 }

cucsSwEthMonSrcEpPeerSlotId OBJECT-TYPE
    SYNTAX       Gauge32
    MAX-ACCESS   read-only
    STATUS       current
    DESCRIPTION
        "Cisco UCS sw:EthMonSrcEp:peerSlotId managed object property"
    ::= { cucsSwEthMonSrcEpEntry 14 }

cucsSwEthMonSrcEpPortId OBJECT-TYPE
    SYNTAX       Gauge32
    MAX-ACCESS   read-only
    STATUS       current
    DESCRIPTION
        "Cisco UCS sw:EthMonSrcEp:portId managed object property"
    ::= { cucsSwEthMonSrcEpEntry 15 }

cucsSwEthMonSrcEpSlotId OBJECT-TYPE
    SYNTAX       Gauge32
    MAX-ACCESS   read-only
    STATUS       current
    DESCRIPTION
        "Cisco UCS sw:EthMonSrcEp:slotId managed object property"
    ::= { cucsSwEthMonSrcEpEntry 16 }

cucsSwEthMonSrcEpSwitchId OBJECT-TYPE
    SYNTAX       CucsNetworkSwitchId
    MAX-ACCESS   read-only
    STATUS       current
    DESCRIPTION
        "Cisco UCS sw:EthMonSrcEp:switchId managed object property"
    ::= { cucsSwEthMonSrcEpEntry 17 }

cucsSwEthMonSrcEpTransport OBJECT-TYPE
    SYNTAX       CucsSwEthMonSrcEpTransport
    MAX-ACCESS   read-only
    STATUS       current
    DESCRIPTION
        "Cisco UCS sw:EthMonSrcEp:transport managed object property"
    ::= { cucsSwEthMonSrcEpEntry 18 }

cucsSwEthMonSrcEpType OBJECT-TYPE
    SYNTAX       CucsNetworkConnectionType
    MAX-ACCESS   read-only
    STATUS       current
    DESCRIPTION
        "Cisco UCS sw:EthMonSrcEp:type managed object property"
    ::= { cucsSwEthMonSrcEpEntry 19 }

cucsSwEthMonSrcEpPeerChassisId OBJECT-TYPE
    SYNTAX       Gauge32
    MAX-ACCESS   read-only
    STATUS       current
    DESCRIPTION
        "Cisco UCS sw:EthMonSrcEp:peerChassisId managed object property"
    ::= { cucsSwEthMonSrcEpEntry 20 }

cucsSwEthMonSrcEpLc OBJECT-TYPE
    SYNTAX       CucsSwPIoEpLc
    MAX-ACCESS   read-only
    STATUS       current
    DESCRIPTION
        "Cisco UCS sw:EthMonSrcEp:lc managed object property"
    ::= { cucsSwEthMonSrcEpEntry 21 }

cucsSwEthTargetEpTable OBJECT-TYPE
    SYNTAX           SEQUENCE OF CucsSwEthTargetEpEntry
    MAX-ACCESS       not-accessible
    STATUS           current
    DESCRIPTION
        "Cisco UCS sw:EthTargetEp managed object table"
    ::= { cucsSwObjects 16 }

cucsSwEthTargetEpEntry OBJECT-TYPE
    SYNTAX           CucsSwEthTargetEpEntry
    MAX-ACCESS       not-accessible
    STATUS           current
    DESCRIPTION
        "Entry for the cucsSwEthTargetEpTable table."
    INDEX { cucsSwEthTargetEpInstanceId }
    ::= { cucsSwEthTargetEpTable 1 }

CucsSwEthTargetEpEntry ::= SEQUENCE {
    cucsSwEthTargetEpInstanceId                                      CucsManagedObjectId,
    cucsSwEthTargetEpDn                                              CucsManagedObjectDn,
    cucsSwEthTargetEpRn                                              SnmpAdminString,
    cucsSwEthTargetEpAdminState                                      CucsFabricExternalEpAdminState,
    cucsSwEthTargetEpChassisId                                       Gauge32,
    cucsSwEthTargetEpEpDn                                            SnmpAdminString,
    cucsSwEthTargetEpIfRole                                          CucsNetworkPortRole,
    cucsSwEthTargetEpIfType                                          CucsFabricPIoEpIfType,
    cucsSwEthTargetEpLicGP                                           Unsigned64,
    cucsSwEthTargetEpLicState                                        CucsLicenseState,
    cucsSwEthTargetEpLocale                                          CucsFabricExternalEpLocale,
    cucsSwEthTargetEpMacAddress                                      MacAddress,
    cucsSwEthTargetEpName                                            SnmpAdminString,
    cucsSwEthTargetEpPeerDn                                          SnmpAdminString,
    cucsSwEthTargetEpPeerPortId                                      Gauge32,
    cucsSwEthTargetEpPeerSlotId                                      Gauge32,
    cucsSwEthTargetEpPortId                                          CucsFabricPIoEpPortId,
    cucsSwEthTargetEpSlotId                                          CucsFabricPIoEpSlotId,
    cucsSwEthTargetEpSwitchId                                        CucsNetworkSwitchId,
    cucsSwEthTargetEpTransport                                       CucsSwEthTargetEpTransport,
    cucsSwEthTargetEpType                                            CucsSwTargetEpType,
    cucsSwEthTargetEpPeerChassisId                                   Gauge32,
    cucsSwEthTargetEpFltAggr                                         Unsigned64
}

cucsSwEthTargetEpInstanceId OBJECT-TYPE
    SYNTAX       CucsManagedObjectId
    MAX-ACCESS   not-accessible
    STATUS       current
    DESCRIPTION
        "Instance identifier of the managed object."
    ::= { cucsSwEthTargetEpEntry 1 }

cucsSwEthTargetEpDn OBJECT-TYPE
    SYNTAX       CucsManagedObjectDn
    MAX-ACCESS   read-only
    STATUS       current
    DESCRIPTION
        "Cisco UCS sw:EthTargetEp:dn managed object property"
    ::= { cucsSwEthTargetEpEntry 2 }

cucsSwEthTargetEpRn OBJECT-TYPE
    SYNTAX       SnmpAdminString
    MAX-ACCESS   read-only
    STATUS       current
    DESCRIPTION
        "Cisco UCS sw:EthTargetEp:rn managed object property"
    ::= { cucsSwEthTargetEpEntry 3 }

cucsSwEthTargetEpAdminState OBJECT-TYPE
    SYNTAX       CucsFabricExternalEpAdminState
    MAX-ACCESS   read-only
    STATUS       current
    DESCRIPTION
        "Cisco UCS sw:EthTargetEp:adminState managed object property"
    ::= { cucsSwEthTargetEpEntry 4 }

cucsSwEthTargetEpChassisId OBJECT-TYPE
    SYNTAX       Gauge32
    MAX-ACCESS   read-only
    STATUS       current
    DESCRIPTION
        "Cisco UCS sw:EthTargetEp:chassisId managed object property"
    ::= { cucsSwEthTargetEpEntry 5 }

cucsSwEthTargetEpEpDn OBJECT-TYPE
    SYNTAX       SnmpAdminString
    MAX-ACCESS   read-only
    STATUS       current
    DESCRIPTION
        "Cisco UCS sw:EthTargetEp:epDn managed object property"
    ::= { cucsSwEthTargetEpEntry 6 }

cucsSwEthTargetEpIfRole OBJECT-TYPE
    SYNTAX       CucsNetworkPortRole
    MAX-ACCESS   read-only
    STATUS       current
    DESCRIPTION
        "Cisco UCS sw:EthTargetEp:ifRole managed object property"
    ::= { cucsSwEthTargetEpEntry 7 }

cucsSwEthTargetEpIfType OBJECT-TYPE
    SYNTAX       CucsFabricPIoEpIfType
    MAX-ACCESS   read-only
    STATUS       current
    DESCRIPTION
        "Cisco UCS sw:EthTargetEp:ifType managed object property"
    ::= { cucsSwEthTargetEpEntry 8 }

cucsSwEthTargetEpLicGP OBJECT-TYPE
    SYNTAX       Unsigned64
    MAX-ACCESS   read-only
    STATUS       current
    DESCRIPTION
        "Cisco UCS sw:EthTargetEp:licGP managed object property"
    ::= { cucsSwEthTargetEpEntry 9 }

cucsSwEthTargetEpLicState OBJECT-TYPE
    SYNTAX       CucsLicenseState
    MAX-ACCESS   read-only
    STATUS       current
    DESCRIPTION
        "Cisco UCS sw:EthTargetEp:licState managed object property"
    ::= { cucsSwEthTargetEpEntry 10 }

cucsSwEthTargetEpLocale OBJECT-TYPE
    SYNTAX       CucsFabricExternalEpLocale
    MAX-ACCESS   read-only
    STATUS       current
    DESCRIPTION
        "Cisco UCS sw:EthTargetEp:locale managed object property"
    ::= { cucsSwEthTargetEpEntry 11 }

cucsSwEthTargetEpMacAddress OBJECT-TYPE
    SYNTAX       MacAddress
    MAX-ACCESS   read-only
    STATUS       current
    DESCRIPTION
        "Cisco UCS sw:EthTargetEp:macAddress managed object property"
    ::= { cucsSwEthTargetEpEntry 12 }

cucsSwEthTargetEpName OBJECT-TYPE
    SYNTAX       SnmpAdminString
    MAX-ACCESS   read-only
    STATUS       current
    DESCRIPTION
        "Cisco UCS sw:EthTargetEp:name managed object property"
    ::= { cucsSwEthTargetEpEntry 13 }

cucsSwEthTargetEpPeerDn OBJECT-TYPE
    SYNTAX       SnmpAdminString
    MAX-ACCESS   read-only
    STATUS       current
    DESCRIPTION
        "Cisco UCS sw:EthTargetEp:peerDn managed object property"
    ::= { cucsSwEthTargetEpEntry 14 }

cucsSwEthTargetEpPeerPortId OBJECT-TYPE
    SYNTAX       Gauge32
    MAX-ACCESS   read-only
    STATUS       current
    DESCRIPTION
        "Cisco UCS sw:EthTargetEp:peerPortId managed object property"
    ::= { cucsSwEthTargetEpEntry 15 }

cucsSwEthTargetEpPeerSlotId OBJECT-TYPE
    SYNTAX       Gauge32
    MAX-ACCESS   read-only
    STATUS       current
    DESCRIPTION
        "Cisco UCS sw:EthTargetEp:peerSlotId managed object property"
    ::= { cucsSwEthTargetEpEntry 16 }

cucsSwEthTargetEpPortId OBJECT-TYPE
    SYNTAX       CucsFabricPIoEpPortId
    MAX-ACCESS   read-only
    STATUS       current
    DESCRIPTION
        "Cisco UCS sw:EthTargetEp:portId managed object property"
    ::= { cucsSwEthTargetEpEntry 17 }

cucsSwEthTargetEpSlotId OBJECT-TYPE
    SYNTAX       CucsFabricPIoEpSlotId
    MAX-ACCESS   read-only
    STATUS       current
    DESCRIPTION
        "Cisco UCS sw:EthTargetEp:slotId managed object property"
    ::= { cucsSwEthTargetEpEntry 18 }

cucsSwEthTargetEpSwitchId OBJECT-TYPE
    SYNTAX       CucsNetworkSwitchId
    MAX-ACCESS   read-only
    STATUS       current
    DESCRIPTION
        "Cisco UCS sw:EthTargetEp:switchId managed object property"
    ::= { cucsSwEthTargetEpEntry 19 }

cucsSwEthTargetEpTransport OBJECT-TYPE
    SYNTAX       CucsSwEthTargetEpTransport
    MAX-ACCESS   read-only
    STATUS       current
    DESCRIPTION
        "Cisco UCS sw:EthTargetEp:transport managed object property"
    ::= { cucsSwEthTargetEpEntry 20 }

cucsSwEthTargetEpType OBJECT-TYPE
    SYNTAX       CucsSwTargetEpType
    MAX-ACCESS   read-only
    STATUS       current
    DESCRIPTION
        "Cisco UCS sw:EthTargetEp:type managed object property"
    ::= { cucsSwEthTargetEpEntry 21 }

cucsSwEthTargetEpPeerChassisId OBJECT-TYPE
    SYNTAX       Gauge32
    MAX-ACCESS   read-only
    STATUS       current
    DESCRIPTION
        "Cisco UCS sw:EthTargetEp:peerChassisId managed object property"
    ::= { cucsSwEthTargetEpEntry 22 }

cucsSwEthTargetEpFltAggr OBJECT-TYPE
    SYNTAX       Unsigned64
    MAX-ACCESS   read-only
    STATUS       current
    DESCRIPTION
        "Cisco UCS sw:EthTargetEp:fltAggr managed object property"
    ::= { cucsSwEthTargetEpEntry 23 }

cucsSwFcEstcEpTable OBJECT-TYPE
    SYNTAX           SEQUENCE OF CucsSwFcEstcEpEntry
    MAX-ACCESS       not-accessible
    STATUS           current
    DESCRIPTION
        "Cisco UCS sw:FcEstcEp managed object table"
    ::= { cucsSwObjects 17 }

cucsSwFcEstcEpEntry OBJECT-TYPE
    SYNTAX           CucsSwFcEstcEpEntry
    MAX-ACCESS       not-accessible
    STATUS           current
    DESCRIPTION
        "Entry for the cucsSwFcEstcEpTable table."
    INDEX { cucsSwFcEstcEpInstanceId }
    ::= { cucsSwFcEstcEpTable 1 }

CucsSwFcEstcEpEntry ::= SEQUENCE {
    cucsSwFcEstcEpInstanceId                                         CucsManagedObjectId,
    cucsSwFcEstcEpDn                                                 CucsManagedObjectDn,
    cucsSwFcEstcEpRn                                                 SnmpAdminString,
    cucsSwFcEstcEpAdminState                                         CucsFabricAdminState,
    cucsSwFcEstcEpChassisId                                          Gauge32,
    cucsSwFcEstcEpEpDn                                               SnmpAdminString,
    cucsSwFcEstcEpIfRole                                             CucsNetworkPortRole,
    cucsSwFcEstcEpIfType                                             CucsSwPIoEpIfType,
    cucsSwFcEstcEpLocale                                             CucsSwEstcEpLocale,
    cucsSwFcEstcEpName                                               SnmpAdminString,
    cucsSwFcEstcEpPeerDn                                             SnmpAdminString,
    cucsSwFcEstcEpPeerPortId                                         Gauge32,
    cucsSwFcEstcEpPeerSlotId                                         Gauge32,
    cucsSwFcEstcEpPortId                                             Gauge32,
    cucsSwFcEstcEpPortVsanId                                         Gauge32,
    cucsSwFcEstcEpSlotId                                             Gauge32,
    cucsSwFcEstcEpSwitchId                                           CucsNetworkSwitchId,
    cucsSwFcEstcEpTransport                                          CucsSwFcEstcEpTransport,
    cucsSwFcEstcEpType                                               CucsNetworkConnectionType,
    cucsSwFcEstcEpPeerChassisId                                      Gauge32,
    cucsSwFcEstcEpLc                                                 CucsSwPIoEpLc
}

cucsSwFcEstcEpInstanceId OBJECT-TYPE
    SYNTAX       CucsManagedObjectId
    MAX-ACCESS   not-accessible
    STATUS       current
    DESCRIPTION
        "Instance identifier of the managed object."
    ::= { cucsSwFcEstcEpEntry 1 }

cucsSwFcEstcEpDn OBJECT-TYPE
    SYNTAX       CucsManagedObjectDn
    MAX-ACCESS   read-only
    STATUS       current
    DESCRIPTION
        "Cisco UCS sw:FcEstcEp:dn managed object property"
    ::= { cucsSwFcEstcEpEntry 2 }

cucsSwFcEstcEpRn OBJECT-TYPE
    SYNTAX       SnmpAdminString
    MAX-ACCESS   read-only
    STATUS       current
    DESCRIPTION
        "Cisco UCS sw:FcEstcEp:rn managed object property"
    ::= { cucsSwFcEstcEpEntry 3 }

cucsSwFcEstcEpAdminState OBJECT-TYPE
    SYNTAX       CucsFabricAdminState
    MAX-ACCESS   read-only
    STATUS       current
    DESCRIPTION
        "Cisco UCS sw:FcEstcEp:adminState managed object property"
    ::= { cucsSwFcEstcEpEntry 4 }

cucsSwFcEstcEpChassisId OBJECT-TYPE
    SYNTAX       Gauge32
    MAX-ACCESS   read-only
    STATUS       current
    DESCRIPTION
        "Cisco UCS sw:FcEstcEp:chassisId managed object property"
    ::= { cucsSwFcEstcEpEntry 5 }

cucsSwFcEstcEpEpDn OBJECT-TYPE
    SYNTAX       SnmpAdminString
    MAX-ACCESS   read-only
    STATUS       current
    DESCRIPTION
        "Cisco UCS sw:FcEstcEp:epDn managed object property"
    ::= { cucsSwFcEstcEpEntry 6 }

cucsSwFcEstcEpIfRole OBJECT-TYPE
    SYNTAX       CucsNetworkPortRole
    MAX-ACCESS   read-only
    STATUS       current
    DESCRIPTION
        "Cisco UCS sw:FcEstcEp:ifRole managed object property"
    ::= { cucsSwFcEstcEpEntry 7 }

cucsSwFcEstcEpIfType OBJECT-TYPE
    SYNTAX       CucsSwPIoEpIfType
    MAX-ACCESS   read-only
    STATUS       current
    DESCRIPTION
        "Cisco UCS sw:FcEstcEp:ifType managed object property"
    ::= { cucsSwFcEstcEpEntry 8 }

cucsSwFcEstcEpLocale OBJECT-TYPE
    SYNTAX       CucsSwEstcEpLocale
    MAX-ACCESS   read-only
    STATUS       current
    DESCRIPTION
        "Cisco UCS sw:FcEstcEp:locale managed object property"
    ::= { cucsSwFcEstcEpEntry 9 }

cucsSwFcEstcEpName OBJECT-TYPE
    SYNTAX       SnmpAdminString
    MAX-ACCESS   read-only
    STATUS       current
    DESCRIPTION
        "Cisco UCS sw:FcEstcEp:name managed object property"
    ::= { cucsSwFcEstcEpEntry 10 }

cucsSwFcEstcEpPeerDn OBJECT-TYPE
    SYNTAX       SnmpAdminString
    MAX-ACCESS   read-only
    STATUS       current
    DESCRIPTION
        "Cisco UCS sw:FcEstcEp:peerDn managed object property"
    ::= { cucsSwFcEstcEpEntry 11 }

cucsSwFcEstcEpPeerPortId OBJECT-TYPE
    SYNTAX       Gauge32
    MAX-ACCESS   read-only
    STATUS       current
    DESCRIPTION
        "Cisco UCS sw:FcEstcEp:peerPortId managed object property"
    ::= { cucsSwFcEstcEpEntry 12 }

cucsSwFcEstcEpPeerSlotId OBJECT-TYPE
    SYNTAX       Gauge32
    MAX-ACCESS   read-only
    STATUS       current
    DESCRIPTION
        "Cisco UCS sw:FcEstcEp:peerSlotId managed object property"
    ::= { cucsSwFcEstcEpEntry 13 }

cucsSwFcEstcEpPortId OBJECT-TYPE
    SYNTAX       Gauge32
    MAX-ACCESS   read-only
    STATUS       current
    DESCRIPTION
        "Cisco UCS sw:FcEstcEp:portId managed object property"
    ::= { cucsSwFcEstcEpEntry 14 }

cucsSwFcEstcEpPortVsanId OBJECT-TYPE
    SYNTAX       Gauge32
    MAX-ACCESS   read-only
    STATUS       current
    DESCRIPTION
        "Cisco UCS sw:FcEstcEp:portVsanId managed object property"
    ::= { cucsSwFcEstcEpEntry 15 }

cucsSwFcEstcEpSlotId OBJECT-TYPE
    SYNTAX       Gauge32
    MAX-ACCESS   read-only
    STATUS       current
    DESCRIPTION
        "Cisco UCS sw:FcEstcEp:slotId managed object property"
    ::= { cucsSwFcEstcEpEntry 16 }

cucsSwFcEstcEpSwitchId OBJECT-TYPE
    SYNTAX       CucsNetworkSwitchId
    MAX-ACCESS   read-only
    STATUS       current
    DESCRIPTION
        "Cisco UCS sw:FcEstcEp:switchId managed object property"
    ::= { cucsSwFcEstcEpEntry 17 }

cucsSwFcEstcEpTransport OBJECT-TYPE
    SYNTAX       CucsSwFcEstcEpTransport
    MAX-ACCESS   read-only
    STATUS       current
    DESCRIPTION
        "Cisco UCS sw:FcEstcEp:transport managed object property"
    ::= { cucsSwFcEstcEpEntry 18 }

cucsSwFcEstcEpType OBJECT-TYPE
    SYNTAX       CucsNetworkConnectionType
    MAX-ACCESS   read-only
    STATUS       current
    DESCRIPTION
        "Cisco UCS sw:FcEstcEp:type managed object property"
    ::= { cucsSwFcEstcEpEntry 19 }

cucsSwFcEstcEpPeerChassisId OBJECT-TYPE
    SYNTAX       Gauge32
    MAX-ACCESS   read-only
    STATUS       current
    DESCRIPTION
        "Cisco UCS sw:FcEstcEp:peerChassisId managed object property"
    ::= { cucsSwFcEstcEpEntry 20 }

cucsSwFcEstcEpLc OBJECT-TYPE
    SYNTAX       CucsSwPIoEpLc
    MAX-ACCESS   read-only
    STATUS       current
    DESCRIPTION
        "Cisco UCS sw:FcEstcEp:lc managed object property"
    ::= { cucsSwFcEstcEpEntry 21 }

cucsSwFcMonTable OBJECT-TYPE
    SYNTAX           SEQUENCE OF CucsSwFcMonEntry
    MAX-ACCESS       not-accessible
    STATUS           current
    DESCRIPTION
        "Cisco UCS sw:FcMon managed object table"
    ::= { cucsSwObjects 18 }

cucsSwFcMonEntry OBJECT-TYPE
    SYNTAX           CucsSwFcMonEntry
    MAX-ACCESS       not-accessible
    STATUS           current
    DESCRIPTION
        "Entry for the cucsSwFcMonTable table."
    INDEX { cucsSwFcMonInstanceId }
    ::= { cucsSwFcMonTable 1 }

CucsSwFcMonEntry ::= SEQUENCE {
    cucsSwFcMonInstanceId                                            CucsManagedObjectId,
    cucsSwFcMonDn                                                    CucsManagedObjectDn,
    cucsSwFcMonRn                                                    SnmpAdminString,
    cucsSwFcMonAdminState                                            CucsSwMonAdminState,
    cucsSwFcMonFsmDescr                                              SnmpAdminString,
    cucsSwFcMonFsmPrev                                               SnmpAdminString,
    cucsSwFcMonFsmProgr                                              Gauge32,
    cucsSwFcMonFsmRmtInvErrCode                                      Gauge32,
    cucsSwFcMonFsmRmtInvErrDescr                                     SnmpAdminString,
    cucsSwFcMonFsmRmtInvRslt                                         CucsConditionRemoteInvRslt,
    cucsSwFcMonFsmStageDescr                                         SnmpAdminString,
    cucsSwFcMonFsmStamp                                              DateAndTime,
    cucsSwFcMonFsmStatus                                             SnmpAdminString,
    cucsSwFcMonFsmTry                                                Gauge32,
    cucsSwFcMonLifeCycle                                             CucsSwMonLifeCycle,
    cucsSwFcMonName                                                  SnmpAdminString,
    cucsSwFcMonSession                                               Gauge32,
    cucsSwFcMonSwitchId                                              CucsNetworkSwitchId,
    cucsSwFcMonTransport                                             CucsSwFcMonTransport,
    cucsSwFcMonType                                                  CucsSwFcMonType,
    cucsSwFcMonHasLastDest                                           TruthValue,
    cucsSwFcMonPeerDn                                                SnmpAdminString
}

cucsSwFcMonInstanceId OBJECT-TYPE
    SYNTAX       CucsManagedObjectId
    MAX-ACCESS   not-accessible
    STATUS       current
    DESCRIPTION
        "Instance identifier of the managed object."
    ::= { cucsSwFcMonEntry 1 }

cucsSwFcMonDn OBJECT-TYPE
    SYNTAX       CucsManagedObjectDn
    MAX-ACCESS   read-only
    STATUS       current
    DESCRIPTION
        "Cisco UCS sw:FcMon:dn managed object property"
    ::= { cucsSwFcMonEntry 2 }

cucsSwFcMonRn OBJECT-TYPE
    SYNTAX       SnmpAdminString
    MAX-ACCESS   read-only
    STATUS       current
    DESCRIPTION
        "Cisco UCS sw:FcMon:rn managed object property"
    ::= { cucsSwFcMonEntry 3 }

cucsSwFcMonAdminState OBJECT-TYPE
    SYNTAX       CucsSwMonAdminState
    MAX-ACCESS   read-only
    STATUS       current
    DESCRIPTION
        "Cisco UCS sw:FcMon:adminState managed object property"
    ::= { cucsSwFcMonEntry 4 }

cucsSwFcMonFsmDescr OBJECT-TYPE
    SYNTAX       SnmpAdminString
    MAX-ACCESS   read-only
    STATUS       current
    DESCRIPTION
        "Cisco UCS sw:FcMon:fsmDescr managed object property"
    ::= { cucsSwFcMonEntry 5 }

cucsSwFcMonFsmPrev OBJECT-TYPE
    SYNTAX       SnmpAdminString
    MAX-ACCESS   read-only
    STATUS       current
    DESCRIPTION
        "Cisco UCS sw:FcMon:fsmPrev managed object property"
    ::= { cucsSwFcMonEntry 6 }

cucsSwFcMonFsmProgr OBJECT-TYPE
    SYNTAX       Gauge32
    MAX-ACCESS   read-only
    STATUS       current
    DESCRIPTION
        "Cisco UCS sw:FcMon:fsmProgr managed object property"
    ::= { cucsSwFcMonEntry 7 }

cucsSwFcMonFsmRmtInvErrCode OBJECT-TYPE
    SYNTAX       Gauge32
    MAX-ACCESS   read-only
    STATUS       current
    DESCRIPTION
        "Cisco UCS sw:FcMon:fsmRmtInvErrCode managed object property"
    ::= { cucsSwFcMonEntry 8 }

cucsSwFcMonFsmRmtInvErrDescr OBJECT-TYPE
    SYNTAX       SnmpAdminString
    MAX-ACCESS   read-only
    STATUS       current
    DESCRIPTION
        "Cisco UCS sw:FcMon:fsmRmtInvErrDescr managed object property"
    ::= { cucsSwFcMonEntry 9 }

cucsSwFcMonFsmRmtInvRslt OBJECT-TYPE
    SYNTAX       CucsConditionRemoteInvRslt
    MAX-ACCESS   read-only
    STATUS       current
    DESCRIPTION
        "Cisco UCS sw:FcMon:fsmRmtInvRslt managed object property"
    ::= { cucsSwFcMonEntry 10 }

cucsSwFcMonFsmStageDescr OBJECT-TYPE
    SYNTAX       SnmpAdminString
    MAX-ACCESS   read-only
    STATUS       current
    DESCRIPTION
        "Cisco UCS sw:FcMon:fsmStageDescr managed object property"
    ::= { cucsSwFcMonEntry 11 }

cucsSwFcMonFsmStamp OBJECT-TYPE
    SYNTAX       DateAndTime
    MAX-ACCESS   read-only
    STATUS       current
    DESCRIPTION
        "Cisco UCS sw:FcMon:fsmStamp managed object property"
    ::= { cucsSwFcMonEntry 12 }

cucsSwFcMonFsmStatus OBJECT-TYPE
    SYNTAX       SnmpAdminString
    MAX-ACCESS   read-only
    STATUS       current
    DESCRIPTION
        "Cisco UCS sw:FcMon:fsmStatus managed object property"
    ::= { cucsSwFcMonEntry 13 }

cucsSwFcMonFsmTry OBJECT-TYPE
    SYNTAX       Gauge32
    MAX-ACCESS   read-only
    STATUS       current
    DESCRIPTION
        "Cisco UCS sw:FcMon:fsmTry managed object property"
    ::= { cucsSwFcMonEntry 14 }

cucsSwFcMonLifeCycle OBJECT-TYPE
    SYNTAX       CucsSwMonLifeCycle
    MAX-ACCESS   read-only
    STATUS       current
    DESCRIPTION
        "Cisco UCS sw:FcMon:lifeCycle managed object property"
    ::= { cucsSwFcMonEntry 15 }

cucsSwFcMonName OBJECT-TYPE
    SYNTAX       SnmpAdminString
    MAX-ACCESS   read-only
    STATUS       current
    DESCRIPTION
        "Cisco UCS sw:FcMon:name managed object property"
    ::= { cucsSwFcMonEntry 16 }

cucsSwFcMonSession OBJECT-TYPE
    SYNTAX       Gauge32
    MAX-ACCESS   read-only
    STATUS       current
    DESCRIPTION
        "Cisco UCS sw:FcMon:session managed object property"
    ::= { cucsSwFcMonEntry 17 }

cucsSwFcMonSwitchId OBJECT-TYPE
    SYNTAX       CucsNetworkSwitchId
    MAX-ACCESS   read-only
    STATUS       current
    DESCRIPTION
        "Cisco UCS sw:FcMon:switchId managed object property"
    ::= { cucsSwFcMonEntry 18 }

cucsSwFcMonTransport OBJECT-TYPE
    SYNTAX       CucsSwFcMonTransport
    MAX-ACCESS   read-only
    STATUS       current
    DESCRIPTION
        "Cisco UCS sw:FcMon:transport managed object property"
    ::= { cucsSwFcMonEntry 19 }

cucsSwFcMonType OBJECT-TYPE
    SYNTAX       CucsSwFcMonType
    MAX-ACCESS   read-only
    STATUS       current
    DESCRIPTION
        "Cisco UCS sw:FcMon:type managed object property"
    ::= { cucsSwFcMonEntry 20 }

cucsSwFcMonHasLastDest OBJECT-TYPE
    SYNTAX       TruthValue
    MAX-ACCESS   read-only
    STATUS       current
    DESCRIPTION
        "Cisco UCS sw:FcMon:hasLastDest managed object property"
    ::= { cucsSwFcMonEntry 21 }

cucsSwFcMonPeerDn OBJECT-TYPE
    SYNTAX       SnmpAdminString
    MAX-ACCESS   read-only
    STATUS       current
    DESCRIPTION
        "Cisco UCS sw:FcMon:peerDn managed object property"
    ::= { cucsSwFcMonEntry 22 }

cucsSwFcMonDestEpTable OBJECT-TYPE
    SYNTAX           SEQUENCE OF CucsSwFcMonDestEpEntry
    MAX-ACCESS       not-accessible
    STATUS           current
    DESCRIPTION
        "Cisco UCS sw:FcMonDestEp managed object table"
    ::= { cucsSwObjects 19 }

cucsSwFcMonDestEpEntry OBJECT-TYPE
    SYNTAX           CucsSwFcMonDestEpEntry
    MAX-ACCESS       not-accessible
    STATUS           current
    DESCRIPTION
        "Entry for the cucsSwFcMonDestEpTable table."
    INDEX { cucsSwFcMonDestEpInstanceId }
    ::= { cucsSwFcMonDestEpTable 1 }

CucsSwFcMonDestEpEntry ::= SEQUENCE {
    cucsSwFcMonDestEpInstanceId                                      CucsManagedObjectId,
    cucsSwFcMonDestEpDn                                              CucsManagedObjectDn,
    cucsSwFcMonDestEpRn                                              SnmpAdminString,
    cucsSwFcMonDestEpAdminState                                      CucsFabricAdminState,
    cucsSwFcMonDestEpChassisId                                       Gauge32,
    cucsSwFcMonDestEpEpDn                                            SnmpAdminString,
    cucsSwFcMonDestEpIfRole                                          CucsNetworkPortRole,
    cucsSwFcMonDestEpIfType                                          CucsSwPIoEpIfType,
    cucsSwFcMonDestEpLocale                                          CucsNetworkLocale,
    cucsSwFcMonDestEpName                                            SnmpAdminString,
    cucsSwFcMonDestEpPeerDn                                          SnmpAdminString,
    cucsSwFcMonDestEpPeerPortId                                      Gauge32,
    cucsSwFcMonDestEpPeerSlotId                                      Gauge32,
    cucsSwFcMonDestEpPortId                                          Gauge32,
    cucsSwFcMonDestEpSlotId                                          Gauge32,
    cucsSwFcMonDestEpSwitchId                                        CucsNetworkSwitchId,
    cucsSwFcMonDestEpTransport                                       CucsSwFcMonDestEpTransport,
    cucsSwFcMonDestEpType                                            CucsNetworkConnectionType,
    cucsSwFcMonDestEpPeerChassisId                                   Gauge32,
    cucsSwFcMonDestEpLc                                              CucsSwPIoEpLc
}

cucsSwFcMonDestEpInstanceId OBJECT-TYPE
    SYNTAX       CucsManagedObjectId
    MAX-ACCESS   not-accessible
    STATUS       current
    DESCRIPTION
        "Instance identifier of the managed object."
    ::= { cucsSwFcMonDestEpEntry 1 }

cucsSwFcMonDestEpDn OBJECT-TYPE
    SYNTAX       CucsManagedObjectDn
    MAX-ACCESS   read-only
    STATUS       current
    DESCRIPTION
        "Cisco UCS sw:FcMonDestEp:dn managed object property"
    ::= { cucsSwFcMonDestEpEntry 2 }

cucsSwFcMonDestEpRn OBJECT-TYPE
    SYNTAX       SnmpAdminString
    MAX-ACCESS   read-only
    STATUS       current
    DESCRIPTION
        "Cisco UCS sw:FcMonDestEp:rn managed object property"
    ::= { cucsSwFcMonDestEpEntry 3 }

cucsSwFcMonDestEpAdminState OBJECT-TYPE
    SYNTAX       CucsFabricAdminState
    MAX-ACCESS   read-only
    STATUS       current
    DESCRIPTION
        "Cisco UCS sw:FcMonDestEp:adminState managed object property"
    ::= { cucsSwFcMonDestEpEntry 4 }

cucsSwFcMonDestEpChassisId OBJECT-TYPE
    SYNTAX       Gauge32
    MAX-ACCESS   read-only
    STATUS       current
    DESCRIPTION
        "Cisco UCS sw:FcMonDestEp:chassisId managed object property"
    ::= { cucsSwFcMonDestEpEntry 5 }

cucsSwFcMonDestEpEpDn OBJECT-TYPE
    SYNTAX       SnmpAdminString
    MAX-ACCESS   read-only
    STATUS       current
    DESCRIPTION
        "Cisco UCS sw:FcMonDestEp:epDn managed object property"
    ::= { cucsSwFcMonDestEpEntry 6 }

cucsSwFcMonDestEpIfRole OBJECT-TYPE
    SYNTAX       CucsNetworkPortRole
    MAX-ACCESS   read-only
    STATUS       current
    DESCRIPTION
        "Cisco UCS sw:FcMonDestEp:ifRole managed object property"
    ::= { cucsSwFcMonDestEpEntry 7 }

cucsSwFcMonDestEpIfType OBJECT-TYPE
    SYNTAX       CucsSwPIoEpIfType
    MAX-ACCESS   read-only
    STATUS       current
    DESCRIPTION
        "Cisco UCS sw:FcMonDestEp:ifType managed object property"
    ::= { cucsSwFcMonDestEpEntry 8 }

cucsSwFcMonDestEpLocale OBJECT-TYPE
    SYNTAX       CucsNetworkLocale
    MAX-ACCESS   read-only
    STATUS       current
    DESCRIPTION
        "Cisco UCS sw:FcMonDestEp:locale managed object property"
    ::= { cucsSwFcMonDestEpEntry 9 }

cucsSwFcMonDestEpName OBJECT-TYPE
    SYNTAX       SnmpAdminString
    MAX-ACCESS   read-only
    STATUS       current
    DESCRIPTION
        "Cisco UCS sw:FcMonDestEp:name managed object property"
    ::= { cucsSwFcMonDestEpEntry 10 }

cucsSwFcMonDestEpPeerDn OBJECT-TYPE
    SYNTAX       SnmpAdminString
    MAX-ACCESS   read-only
    STATUS       current
    DESCRIPTION
        "Cisco UCS sw:FcMonDestEp:peerDn managed object property"
    ::= { cucsSwFcMonDestEpEntry 11 }

cucsSwFcMonDestEpPeerPortId OBJECT-TYPE
    SYNTAX       Gauge32
    MAX-ACCESS   read-only
    STATUS       current
    DESCRIPTION
        "Cisco UCS sw:FcMonDestEp:peerPortId managed object property"
    ::= { cucsSwFcMonDestEpEntry 12 }

cucsSwFcMonDestEpPeerSlotId OBJECT-TYPE
    SYNTAX       Gauge32
    MAX-ACCESS   read-only
    STATUS       current
    DESCRIPTION
        "Cisco UCS sw:FcMonDestEp:peerSlotId managed object property"
    ::= { cucsSwFcMonDestEpEntry 13 }

cucsSwFcMonDestEpPortId OBJECT-TYPE
    SYNTAX       Gauge32
    MAX-ACCESS   read-only
    STATUS       current
    DESCRIPTION
        "Cisco UCS sw:FcMonDestEp:portId managed object property"
    ::= { cucsSwFcMonDestEpEntry 14 }

cucsSwFcMonDestEpSlotId OBJECT-TYPE
    SYNTAX       Gauge32
    MAX-ACCESS   read-only
    STATUS       current
    DESCRIPTION
        "Cisco UCS sw:FcMonDestEp:slotId managed object property"
    ::= { cucsSwFcMonDestEpEntry 15 }

cucsSwFcMonDestEpSwitchId OBJECT-TYPE
    SYNTAX       CucsNetworkSwitchId
    MAX-ACCESS   read-only
    STATUS       current
    DESCRIPTION
        "Cisco UCS sw:FcMonDestEp:switchId managed object property"
    ::= { cucsSwFcMonDestEpEntry 16 }

cucsSwFcMonDestEpTransport OBJECT-TYPE
    SYNTAX       CucsSwFcMonDestEpTransport
    MAX-ACCESS   read-only
    STATUS       current
    DESCRIPTION
        "Cisco UCS sw:FcMonDestEp:transport managed object property"
    ::= { cucsSwFcMonDestEpEntry 17 }

cucsSwFcMonDestEpType OBJECT-TYPE
    SYNTAX       CucsNetworkConnectionType
    MAX-ACCESS   read-only
    STATUS       current
    DESCRIPTION
        "Cisco UCS sw:FcMonDestEp:type managed object property"
    ::= { cucsSwFcMonDestEpEntry 18 }

cucsSwFcMonDestEpPeerChassisId OBJECT-TYPE
    SYNTAX       Gauge32
    MAX-ACCESS   read-only
    STATUS       current
    DESCRIPTION
        "Cisco UCS sw:FcMonDestEp:peerChassisId managed object property"
    ::= { cucsSwFcMonDestEpEntry 19 }

cucsSwFcMonDestEpLc OBJECT-TYPE
    SYNTAX       CucsSwPIoEpLc
    MAX-ACCESS   read-only
    STATUS       current
    DESCRIPTION
        "Cisco UCS sw:FcMonDestEp:lc managed object property"
    ::= { cucsSwFcMonDestEpEntry 20 }

cucsSwFcMonFsmTaskTable OBJECT-TYPE
    SYNTAX           SEQUENCE OF CucsSwFcMonFsmTaskEntry
    MAX-ACCESS       not-accessible
    STATUS           current
    DESCRIPTION
        "Cisco UCS sw:FcMonFsmTask managed object table"
    ::= { cucsSwObjects 20 }

cucsSwFcMonFsmTaskEntry OBJECT-TYPE
    SYNTAX           CucsSwFcMonFsmTaskEntry
    MAX-ACCESS       not-accessible
    STATUS           current
    DESCRIPTION
        "Entry for the cucsSwFcMonFsmTaskTable table."
    INDEX { cucsSwFcMonFsmTaskInstanceId }
    ::= { cucsSwFcMonFsmTaskTable 1 }

CucsSwFcMonFsmTaskEntry ::= SEQUENCE {
    cucsSwFcMonFsmTaskInstanceId                                     CucsManagedObjectId,
    cucsSwFcMonFsmTaskDn                                             CucsManagedObjectDn,
    cucsSwFcMonFsmTaskRn                                             SnmpAdminString,
    cucsSwFcMonFsmTaskCompletion                                     CucsFsmCompletion,
    cucsSwFcMonFsmTaskFlags                                          CucsFsmFlags,
    cucsSwFcMonFsmTaskItem                                           CucsSwFcMonFsmTaskItem,
    cucsSwFcMonFsmTaskSeqId                                          Gauge32
}

cucsSwFcMonFsmTaskInstanceId OBJECT-TYPE
    SYNTAX       CucsManagedObjectId
    MAX-ACCESS   not-accessible
    STATUS       current
    DESCRIPTION
        "Instance identifier of the managed object."
    ::= { cucsSwFcMonFsmTaskEntry 1 }

cucsSwFcMonFsmTaskDn OBJECT-TYPE
    SYNTAX       CucsManagedObjectDn
    MAX-ACCESS   read-only
    STATUS       current
    DESCRIPTION
        "Cisco UCS sw:FcMonFsmTask:dn managed object property"
    ::= { cucsSwFcMonFsmTaskEntry 2 }

cucsSwFcMonFsmTaskRn OBJECT-TYPE
    SYNTAX       SnmpAdminString
    MAX-ACCESS   read-only
    STATUS       current
    DESCRIPTION
        "Cisco UCS sw:FcMonFsmTask:rn managed object property"
    ::= { cucsSwFcMonFsmTaskEntry 3 }

cucsSwFcMonFsmTaskCompletion OBJECT-TYPE
    SYNTAX       CucsFsmCompletion
    MAX-ACCESS   read-only
    STATUS       current
    DESCRIPTION
        "Cisco UCS sw:FcMonFsmTask:completion managed object property"
    ::= { cucsSwFcMonFsmTaskEntry 4 }

cucsSwFcMonFsmTaskFlags OBJECT-TYPE
    SYNTAX       CucsFsmFlags
    MAX-ACCESS   read-only
    STATUS       current
    DESCRIPTION
        "Cisco UCS sw:FcMonFsmTask:flags managed object property"
    ::= { cucsSwFcMonFsmTaskEntry 5 }

cucsSwFcMonFsmTaskItem OBJECT-TYPE
    SYNTAX       CucsSwFcMonFsmTaskItem
    MAX-ACCESS   read-only
    STATUS       current
    DESCRIPTION
        "Cisco UCS sw:FcMonFsmTask:item managed object property"
    ::= { cucsSwFcMonFsmTaskEntry 6 }

cucsSwFcMonFsmTaskSeqId OBJECT-TYPE
    SYNTAX       Gauge32
    MAX-ACCESS   read-only
    STATUS       current
    DESCRIPTION
        "Cisco UCS sw:FcMonFsmTask:seqId managed object property"
    ::= { cucsSwFcMonFsmTaskEntry 7 }

cucsSwFcMonSrcEpTable OBJECT-TYPE
    SYNTAX           SEQUENCE OF CucsSwFcMonSrcEpEntry
    MAX-ACCESS       not-accessible
    STATUS           current
    DESCRIPTION
        "Cisco UCS sw:FcMonSrcEp managed object table"
    ::= { cucsSwObjects 21 }

cucsSwFcMonSrcEpEntry OBJECT-TYPE
    SYNTAX           CucsSwFcMonSrcEpEntry
    MAX-ACCESS       not-accessible
    STATUS           current
    DESCRIPTION
        "Entry for the cucsSwFcMonSrcEpTable table."
    INDEX { cucsSwFcMonSrcEpInstanceId }
    ::= { cucsSwFcMonSrcEpTable 1 }

CucsSwFcMonSrcEpEntry ::= SEQUENCE {
    cucsSwFcMonSrcEpInstanceId                                       CucsManagedObjectId,
    cucsSwFcMonSrcEpDn                                               CucsManagedObjectDn,
    cucsSwFcMonSrcEpRn                                               SnmpAdminString,
    cucsSwFcMonSrcEpAdminState                                       CucsFabricAdminState,
    cucsSwFcMonSrcEpChassisId                                        Gauge32,
    cucsSwFcMonSrcEpEpDn                                             SnmpAdminString,
    cucsSwFcMonSrcEpIfRole                                           CucsNetworkPortRole,
    cucsSwFcMonSrcEpIfType                                           CucsSwPIoEpIfType,
    cucsSwFcMonSrcEpLocale                                           CucsSwMonSrcEpLocale,
    cucsSwFcMonSrcEpMonTrafDir                                       CucsFabricTrafficDirection,
    cucsSwFcMonSrcEpName                                             SnmpAdminString,
    cucsSwFcMonSrcEpPeerDn                                           SnmpAdminString,
    cucsSwFcMonSrcEpPeerPortId                                       Gauge32,
    cucsSwFcMonSrcEpPeerSlotId                                       Gauge32,
    cucsSwFcMonSrcEpPortId                                           Gauge32,
    cucsSwFcMonSrcEpSlotId                                           Gauge32,
    cucsSwFcMonSrcEpSwitchId                                         CucsNetworkSwitchId,
    cucsSwFcMonSrcEpTransport                                        CucsSwFcMonSrcEpTransport,
    cucsSwFcMonSrcEpType                                             CucsNetworkConnectionType,
    cucsSwFcMonSrcEpPeerChassisId                                    Gauge32,
    cucsSwFcMonSrcEpLc                                               CucsSwPIoEpLc
}

cucsSwFcMonSrcEpInstanceId OBJECT-TYPE
    SYNTAX       CucsManagedObjectId
    MAX-ACCESS   not-accessible
    STATUS       current
    DESCRIPTION
        "Instance identifier of the managed object."
    ::= { cucsSwFcMonSrcEpEntry 1 }

cucsSwFcMonSrcEpDn OBJECT-TYPE
    SYNTAX       CucsManagedObjectDn
    MAX-ACCESS   read-only
    STATUS       current
    DESCRIPTION
        "Cisco UCS sw:FcMonSrcEp:dn managed object property"
    ::= { cucsSwFcMonSrcEpEntry 2 }

cucsSwFcMonSrcEpRn OBJECT-TYPE
    SYNTAX       SnmpAdminString
    MAX-ACCESS   read-only
    STATUS       current
    DESCRIPTION
        "Cisco UCS sw:FcMonSrcEp:rn managed object property"
    ::= { cucsSwFcMonSrcEpEntry 3 }

cucsSwFcMonSrcEpAdminState OBJECT-TYPE
    SYNTAX       CucsFabricAdminState
    MAX-ACCESS   read-only
    STATUS       current
    DESCRIPTION
        "Cisco UCS sw:FcMonSrcEp:adminState managed object property"
    ::= { cucsSwFcMonSrcEpEntry 4 }

cucsSwFcMonSrcEpChassisId OBJECT-TYPE
    SYNTAX       Gauge32
    MAX-ACCESS   read-only
    STATUS       current
    DESCRIPTION
        "Cisco UCS sw:FcMonSrcEp:chassisId managed object property"
    ::= { cucsSwFcMonSrcEpEntry 5 }

cucsSwFcMonSrcEpEpDn OBJECT-TYPE
    SYNTAX       SnmpAdminString
    MAX-ACCESS   read-only
    STATUS       current
    DESCRIPTION
        "Cisco UCS sw:FcMonSrcEp:epDn managed object property"
    ::= { cucsSwFcMonSrcEpEntry 6 }

cucsSwFcMonSrcEpIfRole OBJECT-TYPE
    SYNTAX       CucsNetworkPortRole
    MAX-ACCESS   read-only
    STATUS       current
    DESCRIPTION
        "Cisco UCS sw:FcMonSrcEp:ifRole managed object property"
    ::= { cucsSwFcMonSrcEpEntry 7 }

cucsSwFcMonSrcEpIfType OBJECT-TYPE
    SYNTAX       CucsSwPIoEpIfType
    MAX-ACCESS   read-only
    STATUS       current
    DESCRIPTION
        "Cisco UCS sw:FcMonSrcEp:ifType managed object property"
    ::= { cucsSwFcMonSrcEpEntry 8 }

cucsSwFcMonSrcEpLocale OBJECT-TYPE
    SYNTAX       CucsSwMonSrcEpLocale
    MAX-ACCESS   read-only
    STATUS       current
    DESCRIPTION
        "Cisco UCS sw:FcMonSrcEp:locale managed object property"
    ::= { cucsSwFcMonSrcEpEntry 9 }

cucsSwFcMonSrcEpMonTrafDir OBJECT-TYPE
    SYNTAX       CucsFabricTrafficDirection
    MAX-ACCESS   read-only
    STATUS       current
    DESCRIPTION
        "Cisco UCS sw:FcMonSrcEp:monTrafDir managed object property"
    ::= { cucsSwFcMonSrcEpEntry 10 }

cucsSwFcMonSrcEpName OBJECT-TYPE
    SYNTAX       SnmpAdminString
    MAX-ACCESS   read-only
    STATUS       current
    DESCRIPTION
        "Cisco UCS sw:FcMonSrcEp:name managed object property"
    ::= { cucsSwFcMonSrcEpEntry 11 }

cucsSwFcMonSrcEpPeerDn OBJECT-TYPE
    SYNTAX       SnmpAdminString
    MAX-ACCESS   read-only
    STATUS       current
    DESCRIPTION
        "Cisco UCS sw:FcMonSrcEp:peerDn managed object property"
    ::= { cucsSwFcMonSrcEpEntry 12 }

cucsSwFcMonSrcEpPeerPortId OBJECT-TYPE
    SYNTAX       Gauge32
    MAX-ACCESS   read-only
    STATUS       current
    DESCRIPTION
        "Cisco UCS sw:FcMonSrcEp:peerPortId managed object property"
    ::= { cucsSwFcMonSrcEpEntry 13 }

cucsSwFcMonSrcEpPeerSlotId OBJECT-TYPE
    SYNTAX       Gauge32
    MAX-ACCESS   read-only
    STATUS       current
    DESCRIPTION
        "Cisco UCS sw:FcMonSrcEp:peerSlotId managed object property"
    ::= { cucsSwFcMonSrcEpEntry 14 }

cucsSwFcMonSrcEpPortId OBJECT-TYPE
    SYNTAX       Gauge32
    MAX-ACCESS   read-only
    STATUS       current
    DESCRIPTION
        "Cisco UCS sw:FcMonSrcEp:portId managed object property"
    ::= { cucsSwFcMonSrcEpEntry 15 }

cucsSwFcMonSrcEpSlotId OBJECT-TYPE
    SYNTAX       Gauge32
    MAX-ACCESS   read-only
    STATUS       current
    DESCRIPTION
        "Cisco UCS sw:FcMonSrcEp:slotId managed object property"
    ::= { cucsSwFcMonSrcEpEntry 16 }

cucsSwFcMonSrcEpSwitchId OBJECT-TYPE
    SYNTAX       CucsNetworkSwitchId
    MAX-ACCESS   read-only
    STATUS       current
    DESCRIPTION
        "Cisco UCS sw:FcMonSrcEp:switchId managed object property"
    ::= { cucsSwFcMonSrcEpEntry 17 }

cucsSwFcMonSrcEpTransport OBJECT-TYPE
    SYNTAX       CucsSwFcMonSrcEpTransport
    MAX-ACCESS   read-only
    STATUS       current
    DESCRIPTION
        "Cisco UCS sw:FcMonSrcEp:transport managed object property"
    ::= { cucsSwFcMonSrcEpEntry 18 }

cucsSwFcMonSrcEpType OBJECT-TYPE
    SYNTAX       CucsNetworkConnectionType
    MAX-ACCESS   read-only
    STATUS       current
    DESCRIPTION
        "Cisco UCS sw:FcMonSrcEp:type managed object property"
    ::= { cucsSwFcMonSrcEpEntry 19 }

cucsSwFcMonSrcEpPeerChassisId OBJECT-TYPE
    SYNTAX       Gauge32
    MAX-ACCESS   read-only
    STATUS       current
    DESCRIPTION
        "Cisco UCS sw:FcMonSrcEp:peerChassisId managed object property"
    ::= { cucsSwFcMonSrcEpEntry 20 }

cucsSwFcMonSrcEpLc OBJECT-TYPE
    SYNTAX       CucsSwPIoEpLc
    MAX-ACCESS   read-only
    STATUS       current
    DESCRIPTION
        "Cisco UCS sw:FcMonSrcEp:lc managed object property"
    ::= { cucsSwFcMonSrcEpEntry 21 }

cucsSwFcSanBorderTable OBJECT-TYPE
    SYNTAX           SEQUENCE OF CucsSwFcSanBorderEntry
    MAX-ACCESS       not-accessible
    STATUS           current
    DESCRIPTION
        "Cisco UCS sw:FcSanBorder managed object table"
    ::= { cucsSwObjects 22 }

cucsSwFcSanBorderEntry OBJECT-TYPE
    SYNTAX           CucsSwFcSanBorderEntry
    MAX-ACCESS       not-accessible
    STATUS           current
    DESCRIPTION
        "Entry for the cucsSwFcSanBorderTable table."
    INDEX { cucsSwFcSanBorderInstanceId }
    ::= { cucsSwFcSanBorderTable 1 }

CucsSwFcSanBorderEntry ::= SEQUENCE {
    cucsSwFcSanBorderInstanceId                                      CucsManagedObjectId,
    cucsSwFcSanBorderDn                                              CucsManagedObjectDn,
    cucsSwFcSanBorderRn                                              SnmpAdminString,
    cucsSwFcSanBorderFsmDescr                                        SnmpAdminString,
    cucsSwFcSanBorderFsmPrev                                         SnmpAdminString,
    cucsSwFcSanBorderFsmProgr                                        Gauge32,
    cucsSwFcSanBorderFsmRmtInvErrCode                                Gauge32,
    cucsSwFcSanBorderFsmRmtInvErrDescr                               SnmpAdminString,
    cucsSwFcSanBorderFsmRmtInvRslt                                   CucsConditionRemoteInvRslt,
    cucsSwFcSanBorderFsmStageDescr                                   SnmpAdminString,
    cucsSwFcSanBorderFsmStamp                                        DateAndTime,
    cucsSwFcSanBorderFsmStatus                                       SnmpAdminString,
    cucsSwFcSanBorderFsmTry                                          Gauge32,
    cucsSwFcSanBorderLocale                                          CucsSwBorderDomainLocale,
    cucsSwFcSanBorderName                                            SnmpAdminString,
    cucsSwFcSanBorderSwitchId                                        CucsNetworkSwitchId,
    cucsSwFcSanBorderTransport                                       CucsSwFcSanBorderTransport,
    cucsSwFcSanBorderType                                            CucsSwSanBorderType,
    cucsSwFcSanBorderUplinkTrunking                                  CucsSwFcSanBorderUplinkTrunking
}

cucsSwFcSanBorderInstanceId OBJECT-TYPE
    SYNTAX       CucsManagedObjectId
    MAX-ACCESS   not-accessible
    STATUS       current
    DESCRIPTION
        "Instance identifier of the managed object."
    ::= { cucsSwFcSanBorderEntry 1 }

cucsSwFcSanBorderDn OBJECT-TYPE
    SYNTAX       CucsManagedObjectDn
    MAX-ACCESS   read-only
    STATUS       current
    DESCRIPTION
        "Cisco UCS sw:FcSanBorder:dn managed object property"
    ::= { cucsSwFcSanBorderEntry 2 }

cucsSwFcSanBorderRn OBJECT-TYPE
    SYNTAX       SnmpAdminString
    MAX-ACCESS   read-only
    STATUS       current
    DESCRIPTION
        "Cisco UCS sw:FcSanBorder:rn managed object property"
    ::= { cucsSwFcSanBorderEntry 3 }

cucsSwFcSanBorderFsmDescr OBJECT-TYPE
    SYNTAX       SnmpAdminString
    MAX-ACCESS   read-only
    STATUS       current
    DESCRIPTION
        "Cisco UCS sw:FcSanBorder:fsmDescr managed object property"
    ::= { cucsSwFcSanBorderEntry 4 }

cucsSwFcSanBorderFsmPrev OBJECT-TYPE
    SYNTAX       SnmpAdminString
    MAX-ACCESS   read-only
    STATUS       current
    DESCRIPTION
        "Cisco UCS sw:FcSanBorder:fsmPrev managed object property"
    ::= { cucsSwFcSanBorderEntry 5 }

cucsSwFcSanBorderFsmProgr OBJECT-TYPE
    SYNTAX       Gauge32
    MAX-ACCESS   read-only
    STATUS       current
    DESCRIPTION
        "Cisco UCS sw:FcSanBorder:fsmProgr managed object property"
    ::= { cucsSwFcSanBorderEntry 6 }

cucsSwFcSanBorderFsmRmtInvErrCode OBJECT-TYPE
    SYNTAX       Gauge32
    MAX-ACCESS   read-only
    STATUS       current
    DESCRIPTION
        "Cisco UCS sw:FcSanBorder:fsmRmtInvErrCode managed
        object property"
    ::= { cucsSwFcSanBorderEntry 7 }

cucsSwFcSanBorderFsmRmtInvErrDescr OBJECT-TYPE
    SYNTAX       SnmpAdminString
    MAX-ACCESS   read-only
    STATUS       current
    DESCRIPTION
        "Cisco UCS sw:FcSanBorder:fsmRmtInvErrDescr managed
        object property"
    ::= { cucsSwFcSanBorderEntry 8 }

cucsSwFcSanBorderFsmRmtInvRslt OBJECT-TYPE
    SYNTAX       CucsConditionRemoteInvRslt
    MAX-ACCESS   read-only
    STATUS       current
    DESCRIPTION
        "Cisco UCS sw:FcSanBorder:fsmRmtInvRslt managed object property"
    ::= { cucsSwFcSanBorderEntry 9 }

cucsSwFcSanBorderFsmStageDescr OBJECT-TYPE
    SYNTAX       SnmpAdminString
    MAX-ACCESS   read-only
    STATUS       current
    DESCRIPTION
        "Cisco UCS sw:FcSanBorder:fsmStageDescr managed object property"
    ::= { cucsSwFcSanBorderEntry 10 }

cucsSwFcSanBorderFsmStamp OBJECT-TYPE
    SYNTAX       DateAndTime
    MAX-ACCESS   read-only
    STATUS       current
    DESCRIPTION
        "Cisco UCS sw:FcSanBorder:fsmStamp managed object property"
    ::= { cucsSwFcSanBorderEntry 11 }

cucsSwFcSanBorderFsmStatus OBJECT-TYPE
    SYNTAX       SnmpAdminString
    MAX-ACCESS   read-only
    STATUS       current
    DESCRIPTION
        "Cisco UCS sw:FcSanBorder:fsmStatus managed object property"
    ::= { cucsSwFcSanBorderEntry 12 }

cucsSwFcSanBorderFsmTry OBJECT-TYPE
    SYNTAX       Gauge32
    MAX-ACCESS   read-only
    STATUS       current
    DESCRIPTION
        "Cisco UCS sw:FcSanBorder:fsmTry managed object property"
    ::= { cucsSwFcSanBorderEntry 13 }

cucsSwFcSanBorderLocale OBJECT-TYPE
    SYNTAX       CucsSwBorderDomainLocale
    MAX-ACCESS   read-only
    STATUS       current
    DESCRIPTION
        "Cisco UCS sw:FcSanBorder:locale managed object property"
    ::= { cucsSwFcSanBorderEntry 14 }

cucsSwFcSanBorderName OBJECT-TYPE
    SYNTAX       SnmpAdminString
    MAX-ACCESS   read-only
    STATUS       current
    DESCRIPTION
        "Cisco UCS sw:FcSanBorder:name managed object property"
    ::= { cucsSwFcSanBorderEntry 15 }

cucsSwFcSanBorderSwitchId OBJECT-TYPE
    SYNTAX       CucsNetworkSwitchId
    MAX-ACCESS   read-only
    STATUS       current
    DESCRIPTION
        "Cisco UCS sw:FcSanBorder:switchId managed object property"
    ::= { cucsSwFcSanBorderEntry 16 }

cucsSwFcSanBorderTransport OBJECT-TYPE
    SYNTAX       CucsSwFcSanBorderTransport
    MAX-ACCESS   read-only
    STATUS       current
    DESCRIPTION
        "Cisco UCS sw:FcSanBorder:transport managed object property"
    ::= { cucsSwFcSanBorderEntry 17 }

cucsSwFcSanBorderType OBJECT-TYPE
    SYNTAX       CucsSwSanBorderType
    MAX-ACCESS   read-only
    STATUS       current
    DESCRIPTION
        "Cisco UCS sw:FcSanBorder:type managed object property"
    ::= { cucsSwFcSanBorderEntry 18 }

cucsSwFcSanBorderUplinkTrunking OBJECT-TYPE
    SYNTAX       CucsSwFcSanBorderUplinkTrunking
    MAX-ACCESS   read-only
    STATUS       current
    DESCRIPTION
        "Cisco UCS sw:FcSanBorder:uplinkTrunking managed object property"
    ::= { cucsSwFcSanBorderEntry 19 }

cucsSwFcSanBorderFsmTaskTable OBJECT-TYPE
    SYNTAX           SEQUENCE OF CucsSwFcSanBorderFsmTaskEntry
    MAX-ACCESS       not-accessible
    STATUS           current
    DESCRIPTION
        "Cisco UCS sw:FcSanBorderFsmTask managed object table"
    ::= { cucsSwObjects 23 }

cucsSwFcSanBorderFsmTaskEntry OBJECT-TYPE
    SYNTAX           CucsSwFcSanBorderFsmTaskEntry
    MAX-ACCESS       not-accessible
    STATUS           current
    DESCRIPTION
        "Entry for the cucsSwFcSanBorderFsmTaskTable table."
    INDEX { cucsSwFcSanBorderFsmTaskInstanceId }
    ::= { cucsSwFcSanBorderFsmTaskTable 1 }

CucsSwFcSanBorderFsmTaskEntry ::= SEQUENCE {
    cucsSwFcSanBorderFsmTaskInstanceId                               CucsManagedObjectId,
    cucsSwFcSanBorderFsmTaskDn                                       CucsManagedObjectDn,
    cucsSwFcSanBorderFsmTaskRn                                       SnmpAdminString,
    cucsSwFcSanBorderFsmTaskCompletion                               CucsFsmCompletion,
    cucsSwFcSanBorderFsmTaskFlags                                    CucsFsmFlags,
    cucsSwFcSanBorderFsmTaskItem                                     CucsSwFcSanBorderFsmTaskItem,
    cucsSwFcSanBorderFsmTaskSeqId                                    Gauge32
}

cucsSwFcSanBorderFsmTaskInstanceId OBJECT-TYPE
    SYNTAX       CucsManagedObjectId
    MAX-ACCESS   not-accessible
    STATUS       current
    DESCRIPTION
        "Instance identifier of the managed object."
    ::= { cucsSwFcSanBorderFsmTaskEntry 1 }

cucsSwFcSanBorderFsmTaskDn OBJECT-TYPE
    SYNTAX       CucsManagedObjectDn
    MAX-ACCESS   read-only
    STATUS       current
    DESCRIPTION
        "Cisco UCS sw:FcSanBorderFsmTask:dn managed object property"
    ::= { cucsSwFcSanBorderFsmTaskEntry 2 }

cucsSwFcSanBorderFsmTaskRn OBJECT-TYPE
    SYNTAX       SnmpAdminString
    MAX-ACCESS   read-only
    STATUS       current
    DESCRIPTION
        "Cisco UCS sw:FcSanBorderFsmTask:rn managed object property"
    ::= { cucsSwFcSanBorderFsmTaskEntry 3 }

cucsSwFcSanBorderFsmTaskCompletion OBJECT-TYPE
    SYNTAX       CucsFsmCompletion
    MAX-ACCESS   read-only
    STATUS       current
    DESCRIPTION
        "Cisco UCS sw:FcSanBorderFsmTask:completion managed
        object property"
    ::= { cucsSwFcSanBorderFsmTaskEntry 4 }

cucsSwFcSanBorderFsmTaskFlags OBJECT-TYPE
    SYNTAX       CucsFsmFlags
    MAX-ACCESS   read-only
    STATUS       current
    DESCRIPTION
        "Cisco UCS sw:FcSanBorderFsmTask:flags managed object property"
    ::= { cucsSwFcSanBorderFsmTaskEntry 5 }

cucsSwFcSanBorderFsmTaskItem OBJECT-TYPE
    SYNTAX       CucsSwFcSanBorderFsmTaskItem
    MAX-ACCESS   read-only
    STATUS       current
    DESCRIPTION
        "Cisco UCS sw:FcSanBorderFsmTask:item managed object property"
    ::= { cucsSwFcSanBorderFsmTaskEntry 6 }

cucsSwFcSanBorderFsmTaskSeqId OBJECT-TYPE
    SYNTAX       Gauge32
    MAX-ACCESS   read-only
    STATUS       current
    DESCRIPTION
        "Cisco UCS sw:FcSanBorderFsmTask:seqId managed object property"
    ::= { cucsSwFcSanBorderFsmTaskEntry 7 }

cucsSwFcSanEpTable OBJECT-TYPE
    SYNTAX           SEQUENCE OF CucsSwFcSanEpEntry
    MAX-ACCESS       not-accessible
    STATUS           current
    DESCRIPTION
        "Cisco UCS sw:FcSanEp managed object table"
    ::= { cucsSwObjects 24 }

cucsSwFcSanEpEntry OBJECT-TYPE
    SYNTAX           CucsSwFcSanEpEntry
    MAX-ACCESS       not-accessible
    STATUS           current
    DESCRIPTION
        "Entry for the cucsSwFcSanEpTable table."
    INDEX { cucsSwFcSanEpInstanceId }
    ::= { cucsSwFcSanEpTable 1 }

CucsSwFcSanEpEntry ::= SEQUENCE {
    cucsSwFcSanEpInstanceId                                          CucsManagedObjectId,
    cucsSwFcSanEpDn                                                  CucsManagedObjectDn,
    cucsSwFcSanEpRn                                                  SnmpAdminString,
    cucsSwFcSanEpAdminState                                          CucsFabricAdminState,
    cucsSwFcSanEpChassisId                                           Gauge32,
    cucsSwFcSanEpEpDn                                                SnmpAdminString,
    cucsSwFcSanEpIfRole                                              CucsSwSanEpIfRole,
    cucsSwFcSanEpIfType                                              CucsSwPIoEpIfType,
    cucsSwFcSanEpLocale                                              CucsSwBorderEpLocale,
    cucsSwFcSanEpName                                                SnmpAdminString,
    cucsSwFcSanEpPcId                                                Gauge32,
    cucsSwFcSanEpPeerDn                                              SnmpAdminString,
    cucsSwFcSanEpPeerPortId                                          Gauge32,
    cucsSwFcSanEpPeerSlotId                                          Gauge32,
    cucsSwFcSanEpPortId                                              Gauge32,
    cucsSwFcSanEpPortVsanId                                          Gauge32,
    cucsSwFcSanEpSlotId                                              Gauge32,
    cucsSwFcSanEpSwitchId                                            CucsNetworkSwitchId,
    cucsSwFcSanEpTransport                                           CucsSwFcSanEpTransport,
    cucsSwFcSanEpType                                                CucsSwSanEpType,
    cucsSwFcSanEpAdminSpeed                                          CucsPortSpeed,
    cucsSwFcSanEpPeerChassisId                                       Gauge32,
    cucsSwFcSanEpLc                                                  CucsSwPIoEpLc
}

cucsSwFcSanEpInstanceId OBJECT-TYPE
    SYNTAX       CucsManagedObjectId
    MAX-ACCESS   not-accessible
    STATUS       current
    DESCRIPTION
        "Instance identifier of the managed object."
    ::= { cucsSwFcSanEpEntry 1 }

cucsSwFcSanEpDn OBJECT-TYPE
    SYNTAX       CucsManagedObjectDn
    MAX-ACCESS   read-only
    STATUS       current
    DESCRIPTION
        "Cisco UCS sw:FcSanEp:dn managed object property"
    ::= { cucsSwFcSanEpEntry 2 }

cucsSwFcSanEpRn OBJECT-TYPE
    SYNTAX       SnmpAdminString
    MAX-ACCESS   read-only
    STATUS       current
    DESCRIPTION
        "Cisco UCS sw:FcSanEp:rn managed object property"
    ::= { cucsSwFcSanEpEntry 3 }

cucsSwFcSanEpAdminState OBJECT-TYPE
    SYNTAX       CucsFabricAdminState
    MAX-ACCESS   read-only
    STATUS       current
    DESCRIPTION
        "Cisco UCS sw:FcSanEp:adminState managed object property"
    ::= { cucsSwFcSanEpEntry 4 }

cucsSwFcSanEpChassisId OBJECT-TYPE
    SYNTAX       Gauge32
    MAX-ACCESS   read-only
    STATUS       current
    DESCRIPTION
        "Cisco UCS sw:FcSanEp:chassisId managed object property"
    ::= { cucsSwFcSanEpEntry 5 }

cucsSwFcSanEpEpDn OBJECT-TYPE
    SYNTAX       SnmpAdminString
    MAX-ACCESS   read-only
    STATUS       current
    DESCRIPTION
        "Cisco UCS sw:FcSanEp:epDn managed object property"
    ::= { cucsSwFcSanEpEntry 6 }

cucsSwFcSanEpIfRole OBJECT-TYPE
    SYNTAX       CucsSwSanEpIfRole
    MAX-ACCESS   read-only
    STATUS       current
    DESCRIPTION
        "Cisco UCS sw:FcSanEp:ifRole managed object property"
    ::= { cucsSwFcSanEpEntry 7 }

cucsSwFcSanEpIfType OBJECT-TYPE
    SYNTAX       CucsSwPIoEpIfType
    MAX-ACCESS   read-only
    STATUS       current
    DESCRIPTION
        "Cisco UCS sw:FcSanEp:ifType managed object property"
    ::= { cucsSwFcSanEpEntry 8 }

cucsSwFcSanEpLocale OBJECT-TYPE
    SYNTAX       CucsSwBorderEpLocale
    MAX-ACCESS   read-only
    STATUS       current
    DESCRIPTION
        "Cisco UCS sw:FcSanEp:locale managed object property"
    ::= { cucsSwFcSanEpEntry 9 }

cucsSwFcSanEpName OBJECT-TYPE
    SYNTAX       SnmpAdminString
    MAX-ACCESS   read-only
    STATUS       current
    DESCRIPTION
        "Cisco UCS sw:FcSanEp:name managed object property"
    ::= { cucsSwFcSanEpEntry 10 }

cucsSwFcSanEpPcId OBJECT-TYPE
    SYNTAX       Gauge32
    MAX-ACCESS   read-only
    STATUS       current
    DESCRIPTION
        "Cisco UCS sw:FcSanEp:pcId managed object property"
    ::= { cucsSwFcSanEpEntry 11 }

cucsSwFcSanEpPeerDn OBJECT-TYPE
    SYNTAX       SnmpAdminString
    MAX-ACCESS   read-only
    STATUS       current
    DESCRIPTION
        "Cisco UCS sw:FcSanEp:peerDn managed object property"
    ::= { cucsSwFcSanEpEntry 12 }

cucsSwFcSanEpPeerPortId OBJECT-TYPE
    SYNTAX       Gauge32
    MAX-ACCESS   read-only
    STATUS       current
    DESCRIPTION
        "Cisco UCS sw:FcSanEp:peerPortId managed object property"
    ::= { cucsSwFcSanEpEntry 13 }

cucsSwFcSanEpPeerSlotId OBJECT-TYPE
    SYNTAX       Gauge32
    MAX-ACCESS   read-only
    STATUS       current
    DESCRIPTION
        "Cisco UCS sw:FcSanEp:peerSlotId managed object property"
    ::= { cucsSwFcSanEpEntry 14 }

cucsSwFcSanEpPortId OBJECT-TYPE
    SYNTAX       Gauge32
    MAX-ACCESS   read-only
    STATUS       current
    DESCRIPTION
        "Cisco UCS sw:FcSanEp:portId managed object property"
    ::= { cucsSwFcSanEpEntry 15 }

cucsSwFcSanEpPortVsanId OBJECT-TYPE
    SYNTAX       Gauge32
    MAX-ACCESS   read-only
    STATUS       current
    DESCRIPTION
        "Cisco UCS sw:FcSanEp:portVsanId managed object property"
    ::= { cucsSwFcSanEpEntry 16 }

cucsSwFcSanEpSlotId OBJECT-TYPE
    SYNTAX       Gauge32
    MAX-ACCESS   read-only
    STATUS       current
    DESCRIPTION
        "Cisco UCS sw:FcSanEp:slotId managed object property"
    ::= { cucsSwFcSanEpEntry 17 }

cucsSwFcSanEpSwitchId OBJECT-TYPE
    SYNTAX       CucsNetworkSwitchId
    MAX-ACCESS   read-only
    STATUS       current
    DESCRIPTION
        "Cisco UCS sw:FcSanEp:switchId managed object property"
    ::= { cucsSwFcSanEpEntry 18 }

cucsSwFcSanEpTransport OBJECT-TYPE
    SYNTAX       CucsSwFcSanEpTransport
    MAX-ACCESS   read-only
    STATUS       current
    DESCRIPTION
        "Cisco UCS sw:FcSanEp:transport managed object property"
    ::= { cucsSwFcSanEpEntry 19 }

cucsSwFcSanEpType OBJECT-TYPE
    SYNTAX       CucsSwSanEpType
    MAX-ACCESS   read-only
    STATUS       current
    DESCRIPTION
        "Cisco UCS sw:FcSanEp:type managed object property"
    ::= { cucsSwFcSanEpEntry 20 }

cucsSwFcSanEpAdminSpeed OBJECT-TYPE
    SYNTAX       CucsPortSpeed
    MAX-ACCESS   read-only
    STATUS       current
    DESCRIPTION
        "Cisco UCS sw:FcSanEp:adminSpeed managed object property"
    ::= { cucsSwFcSanEpEntry 21 }

cucsSwFcSanEpPeerChassisId OBJECT-TYPE
    SYNTAX       Gauge32
    MAX-ACCESS   read-only
    STATUS       current
    DESCRIPTION
        "Cisco UCS sw:FcSanEp:peerChassisId managed object property"
    ::= { cucsSwFcSanEpEntry 22 }

cucsSwFcSanEpLc OBJECT-TYPE
    SYNTAX       CucsSwPIoEpLc
    MAX-ACCESS   read-only
    STATUS       current
    DESCRIPTION
        "Cisco UCS sw:FcSanEp:lc managed object property"
    ::= { cucsSwFcSanEpEntry 23 }

cucsSwFcSanMonTable OBJECT-TYPE
    SYNTAX           SEQUENCE OF CucsSwFcSanMonEntry
    MAX-ACCESS       not-accessible
    STATUS           current
    DESCRIPTION
        "Cisco UCS sw:FcSanMon managed object table"
    ::= { cucsSwObjects 25 }

cucsSwFcSanMonEntry OBJECT-TYPE
    SYNTAX           CucsSwFcSanMonEntry
    MAX-ACCESS       not-accessible
    STATUS           current
    DESCRIPTION
        "Entry for the cucsSwFcSanMonTable table."
    INDEX { cucsSwFcSanMonInstanceId }
    ::= { cucsSwFcSanMonTable 1 }

CucsSwFcSanMonEntry ::= SEQUENCE {
    cucsSwFcSanMonInstanceId                                         CucsManagedObjectId,
    cucsSwFcSanMonDn                                                 CucsManagedObjectDn,
    cucsSwFcSanMonRn                                                 SnmpAdminString,
    cucsSwFcSanMonLocale                                             CucsSwMonDomainLocale,
    cucsSwFcSanMonName                                               SnmpAdminString,
    cucsSwFcSanMonSwitchId                                           CucsNetworkSwitchId,
    cucsSwFcSanMonTransport                                          CucsSwFcSanMonTransport,
    cucsSwFcSanMonType                                               CucsSwSanMonType
}

cucsSwFcSanMonInstanceId OBJECT-TYPE
    SYNTAX       CucsManagedObjectId
    MAX-ACCESS   not-accessible
    STATUS       current
    DESCRIPTION
        "Instance identifier of the managed object."
    ::= { cucsSwFcSanMonEntry 1 }

cucsSwFcSanMonDn OBJECT-TYPE
    SYNTAX       CucsManagedObjectDn
    MAX-ACCESS   read-only
    STATUS       current
    DESCRIPTION
        "Cisco UCS sw:FcSanMon:dn managed object property"
    ::= { cucsSwFcSanMonEntry 2 }

cucsSwFcSanMonRn OBJECT-TYPE
    SYNTAX       SnmpAdminString
    MAX-ACCESS   read-only
    STATUS       current
    DESCRIPTION
        "Cisco UCS sw:FcSanMon:rn managed object property"
    ::= { cucsSwFcSanMonEntry 3 }

cucsSwFcSanMonLocale OBJECT-TYPE
    SYNTAX       CucsSwMonDomainLocale
    MAX-ACCESS   read-only
    STATUS       current
    DESCRIPTION
        "Cisco UCS sw:FcSanMon:locale managed object property"
    ::= { cucsSwFcSanMonEntry 4 }

cucsSwFcSanMonName OBJECT-TYPE
    SYNTAX       SnmpAdminString
    MAX-ACCESS   read-only
    STATUS       current
    DESCRIPTION
        "Cisco UCS sw:FcSanMon:name managed object property"
    ::= { cucsSwFcSanMonEntry 5 }

cucsSwFcSanMonSwitchId OBJECT-TYPE
    SYNTAX       CucsNetworkSwitchId
    MAX-ACCESS   read-only
    STATUS       current
    DESCRIPTION
        "Cisco UCS sw:FcSanMon:switchId managed object property"
    ::= { cucsSwFcSanMonEntry 6 }

cucsSwFcSanMonTransport OBJECT-TYPE
    SYNTAX       CucsSwFcSanMonTransport
    MAX-ACCESS   read-only
    STATUS       current
    DESCRIPTION
        "Cisco UCS sw:FcSanMon:transport managed object property"
    ::= { cucsSwFcSanMonEntry 7 }

cucsSwFcSanMonType OBJECT-TYPE
    SYNTAX       CucsSwSanMonType
    MAX-ACCESS   read-only
    STATUS       current
    DESCRIPTION
        "Cisco UCS sw:FcSanMon:type managed object property"
    ::= { cucsSwFcSanMonEntry 8 }

cucsSwFcSanPcTable OBJECT-TYPE
    SYNTAX           SEQUENCE OF CucsSwFcSanPcEntry
    MAX-ACCESS       not-accessible
    STATUS           current
    DESCRIPTION
        "Cisco UCS sw:FcSanPc managed object table"
    ::= { cucsSwObjects 26 }

cucsSwFcSanPcEntry OBJECT-TYPE
    SYNTAX           CucsSwFcSanPcEntry
    MAX-ACCESS       not-accessible
    STATUS           current
    DESCRIPTION
        "Entry for the cucsSwFcSanPcTable table."
    INDEX { cucsSwFcSanPcInstanceId }
    ::= { cucsSwFcSanPcTable 1 }

CucsSwFcSanPcEntry ::= SEQUENCE {
    cucsSwFcSanPcInstanceId                                          CucsManagedObjectId,
    cucsSwFcSanPcDn                                                  CucsManagedObjectDn,
    cucsSwFcSanPcRn                                                  SnmpAdminString,
    cucsSwFcSanPcAdminState                                          CucsFabricAdminState,
    cucsSwFcSanPcEpDn                                                SnmpAdminString,
    cucsSwFcSanPcIfRole                                              CucsSwSanPcIfRole,
    cucsSwFcSanPcIfType                                              CucsSwCIoEpIfType,
    cucsSwFcSanPcLocale                                              CucsSwBorderPcLocale,
    cucsSwFcSanPcName                                                SnmpAdminString,
    cucsSwFcSanPcPcId                                                Gauge32,
    cucsSwFcSanPcPeerDn                                              SnmpAdminString,
    cucsSwFcSanPcPortId                                              Gauge32,
    cucsSwFcSanPcPortVsanId                                          Gauge32,
    cucsSwFcSanPcSwitchId                                            CucsNetworkSwitchId,
    cucsSwFcSanPcTransport                                           CucsSwFcSanPcTransport,
    cucsSwFcSanPcType                                                CucsSwSanPcType,
    cucsSwFcSanPcMonTrafDir                                          CucsFabricTrafficDirection,
    cucsSwFcSanPcAdminSpeed                                          CucsPortSpeed
}

cucsSwFcSanPcInstanceId OBJECT-TYPE
    SYNTAX       CucsManagedObjectId
    MAX-ACCESS   not-accessible
    STATUS       current
    DESCRIPTION
        "Instance identifier of the managed object."
    ::= { cucsSwFcSanPcEntry 1 }

cucsSwFcSanPcDn OBJECT-TYPE
    SYNTAX       CucsManagedObjectDn
    MAX-ACCESS   read-only
    STATUS       current
    DESCRIPTION
        "Cisco UCS sw:FcSanPc:dn managed object property"
    ::= { cucsSwFcSanPcEntry 2 }

cucsSwFcSanPcRn OBJECT-TYPE
    SYNTAX       SnmpAdminString
    MAX-ACCESS   read-only
    STATUS       current
    DESCRIPTION
        "Cisco UCS sw:FcSanPc:rn managed object property"
    ::= { cucsSwFcSanPcEntry 3 }

cucsSwFcSanPcAdminState OBJECT-TYPE
    SYNTAX       CucsFabricAdminState
    MAX-ACCESS   read-only
    STATUS       current
    DESCRIPTION
        "Cisco UCS sw:FcSanPc:adminState managed object property"
    ::= { cucsSwFcSanPcEntry 4 }

cucsSwFcSanPcEpDn OBJECT-TYPE
    SYNTAX       SnmpAdminString
    MAX-ACCESS   read-only
    STATUS       current
    DESCRIPTION
        "Cisco UCS sw:FcSanPc:epDn managed object property"
    ::= { cucsSwFcSanPcEntry 5 }

cucsSwFcSanPcIfRole OBJECT-TYPE
    SYNTAX       CucsSwSanPcIfRole
    MAX-ACCESS   read-only
    STATUS       current
    DESCRIPTION
        "Cisco UCS sw:FcSanPc:ifRole managed object property"
    ::= { cucsSwFcSanPcEntry 6 }

cucsSwFcSanPcIfType OBJECT-TYPE
    SYNTAX       CucsSwCIoEpIfType
    MAX-ACCESS   read-only
    STATUS       current
    DESCRIPTION
        "Cisco UCS sw:FcSanPc:ifType managed object property"
    ::= { cucsSwFcSanPcEntry 7 }

cucsSwFcSanPcLocale OBJECT-TYPE
    SYNTAX       CucsSwBorderPcLocale
    MAX-ACCESS   read-only
    STATUS       current
    DESCRIPTION
        "Cisco UCS sw:FcSanPc:locale managed object property"
    ::= { cucsSwFcSanPcEntry 8 }

cucsSwFcSanPcName OBJECT-TYPE
    SYNTAX       SnmpAdminString
    MAX-ACCESS   read-only
    STATUS       current
    DESCRIPTION
        "Cisco UCS sw:FcSanPc:name managed object property"
    ::= { cucsSwFcSanPcEntry 9 }

cucsSwFcSanPcPcId OBJECT-TYPE
    SYNTAX       Gauge32
    MAX-ACCESS   read-only
    STATUS       current
    DESCRIPTION
        "Cisco UCS sw:FcSanPc:pcId managed object property"
    ::= { cucsSwFcSanPcEntry 10 }

cucsSwFcSanPcPeerDn OBJECT-TYPE
    SYNTAX       SnmpAdminString
    MAX-ACCESS   read-only
    STATUS       current
    DESCRIPTION
        "Cisco UCS sw:FcSanPc:peerDn managed object property"
    ::= { cucsSwFcSanPcEntry 11 }

cucsSwFcSanPcPortId OBJECT-TYPE
    SYNTAX       Gauge32
    MAX-ACCESS   read-only
    STATUS       current
    DESCRIPTION
        "Cisco UCS sw:FcSanPc:portId managed object property"
    ::= { cucsSwFcSanPcEntry 12 }

cucsSwFcSanPcPortVsanId OBJECT-TYPE
    SYNTAX       Gauge32
    MAX-ACCESS   read-only
    STATUS       current
    DESCRIPTION
        "Cisco UCS sw:FcSanPc:portVsanId managed object property"
    ::= { cucsSwFcSanPcEntry 13 }

cucsSwFcSanPcSwitchId OBJECT-TYPE
    SYNTAX       CucsNetworkSwitchId
    MAX-ACCESS   read-only
    STATUS       current
    DESCRIPTION
        "Cisco UCS sw:FcSanPc:switchId managed object property"
    ::= { cucsSwFcSanPcEntry 14 }

cucsSwFcSanPcTransport OBJECT-TYPE
    SYNTAX       CucsSwFcSanPcTransport
    MAX-ACCESS   read-only
    STATUS       current
    DESCRIPTION
        "Cisco UCS sw:FcSanPc:transport managed object property"
    ::= { cucsSwFcSanPcEntry 15 }

cucsSwFcSanPcType OBJECT-TYPE
    SYNTAX       CucsSwSanPcType
    MAX-ACCESS   read-only
    STATUS       current
    DESCRIPTION
        "Cisco UCS sw:FcSanPc:type managed object property"
    ::= { cucsSwFcSanPcEntry 16 }

cucsSwFcSanPcMonTrafDir OBJECT-TYPE
    SYNTAX       CucsFabricTrafficDirection
    MAX-ACCESS   read-only
    STATUS       current
    DESCRIPTION
        "Cisco UCS sw:FcSanPc:monTrafDir managed object property"
    ::= { cucsSwFcSanPcEntry 17 }

cucsSwFcSanPcAdminSpeed OBJECT-TYPE
    SYNTAX       CucsPortSpeed
    MAX-ACCESS   read-only
    STATUS       current
    DESCRIPTION
        "Cisco UCS sw:FcSanPc:adminSpeed managed object property"
    ::= { cucsSwFcSanPcEntry 18 }

cucsSwFcoeEstcEpTable OBJECT-TYPE
    SYNTAX           SEQUENCE OF CucsSwFcoeEstcEpEntry
    MAX-ACCESS       not-accessible
    STATUS           current
    DESCRIPTION
        "Cisco UCS sw:FcoeEstcEp managed object table"
    ::= { cucsSwObjects 27 }

cucsSwFcoeEstcEpEntry OBJECT-TYPE
    SYNTAX           CucsSwFcoeEstcEpEntry
    MAX-ACCESS       not-accessible
    STATUS           current
    DESCRIPTION
        "Entry for the cucsSwFcoeEstcEpTable table."
    INDEX { cucsSwFcoeEstcEpInstanceId }
    ::= { cucsSwFcoeEstcEpTable 1 }

CucsSwFcoeEstcEpEntry ::= SEQUENCE {
    cucsSwFcoeEstcEpInstanceId                                       CucsManagedObjectId,
    cucsSwFcoeEstcEpDn                                               CucsManagedObjectDn,
    cucsSwFcoeEstcEpRn                                               SnmpAdminString,
    cucsSwFcoeEstcEpAdminState                                       CucsFabricAdminState,
    cucsSwFcoeEstcEpChassisId                                        Gauge32,
    cucsSwFcoeEstcEpEpDn                                             SnmpAdminString,
    cucsSwFcoeEstcEpIfRole                                           CucsNetworkPortRole,
    cucsSwFcoeEstcEpIfType                                           CucsSwPIoEpIfType,
    cucsSwFcoeEstcEpLocale                                           CucsSwEstcEpLocale,
    cucsSwFcoeEstcEpName                                             SnmpAdminString,
    cucsSwFcoeEstcEpPeerDn                                           SnmpAdminString,
    cucsSwFcoeEstcEpPeerPortId                                       Gauge32,
    cucsSwFcoeEstcEpPeerSlotId                                       Gauge32,
    cucsSwFcoeEstcEpPortId                                           Gauge32,
    cucsSwFcoeEstcEpSlotId                                           Gauge32,
    cucsSwFcoeEstcEpSwitchId                                         CucsNetworkSwitchId,
    cucsSwFcoeEstcEpTransport                                        CucsSwFcoeEstcEpTransport,
    cucsSwFcoeEstcEpType                                             CucsNetworkConnectionType,
    cucsSwFcoeEstcEpPeerChassisId                                    Gauge32,
    cucsSwFcoeEstcEpLc                                               CucsSwPIoEpLc
}

cucsSwFcoeEstcEpInstanceId OBJECT-TYPE
    SYNTAX       CucsManagedObjectId
    MAX-ACCESS   not-accessible
    STATUS       current
    DESCRIPTION
        "Instance identifier of the managed object."
    ::= { cucsSwFcoeEstcEpEntry 1 }

cucsSwFcoeEstcEpDn OBJECT-TYPE
    SYNTAX       CucsManagedObjectDn
    MAX-ACCESS   read-only
    STATUS       current
    DESCRIPTION
        "Cisco UCS sw:FcoeEstcEp:dn managed object property"
    ::= { cucsSwFcoeEstcEpEntry 2 }

cucsSwFcoeEstcEpRn OBJECT-TYPE
    SYNTAX       SnmpAdminString
    MAX-ACCESS   read-only
    STATUS       current
    DESCRIPTION
        "Cisco UCS sw:FcoeEstcEp:rn managed object property"
    ::= { cucsSwFcoeEstcEpEntry 3 }

cucsSwFcoeEstcEpAdminState OBJECT-TYPE
    SYNTAX       CucsFabricAdminState
    MAX-ACCESS   read-only
    STATUS       current
    DESCRIPTION
        "Cisco UCS sw:FcoeEstcEp:adminState managed object property"
    ::= { cucsSwFcoeEstcEpEntry 4 }

cucsSwFcoeEstcEpChassisId OBJECT-TYPE
    SYNTAX       Gauge32
    MAX-ACCESS   read-only
    STATUS       current
    DESCRIPTION
        "Cisco UCS sw:FcoeEstcEp:chassisId managed object property"
    ::= { cucsSwFcoeEstcEpEntry 5 }

cucsSwFcoeEstcEpEpDn OBJECT-TYPE
    SYNTAX       SnmpAdminString
    MAX-ACCESS   read-only
    STATUS       current
    DESCRIPTION
        "Cisco UCS sw:FcoeEstcEp:epDn managed object property"
    ::= { cucsSwFcoeEstcEpEntry 6 }

cucsSwFcoeEstcEpIfRole OBJECT-TYPE
    SYNTAX       CucsNetworkPortRole
    MAX-ACCESS   read-only
    STATUS       current
    DESCRIPTION
        "Cisco UCS sw:FcoeEstcEp:ifRole managed object property"
    ::= { cucsSwFcoeEstcEpEntry 7 }

cucsSwFcoeEstcEpIfType OBJECT-TYPE
    SYNTAX       CucsSwPIoEpIfType
    MAX-ACCESS   read-only
    STATUS       current
    DESCRIPTION
        "Cisco UCS sw:FcoeEstcEp:ifType managed object property"
    ::= { cucsSwFcoeEstcEpEntry 8 }

cucsSwFcoeEstcEpLocale OBJECT-TYPE
    SYNTAX       CucsSwEstcEpLocale
    MAX-ACCESS   read-only
    STATUS       current
    DESCRIPTION
        "Cisco UCS sw:FcoeEstcEp:locale managed object property"
    ::= { cucsSwFcoeEstcEpEntry 9 }

cucsSwFcoeEstcEpName OBJECT-TYPE
    SYNTAX       SnmpAdminString
    MAX-ACCESS   read-only
    STATUS       current
    DESCRIPTION
        "Cisco UCS sw:FcoeEstcEp:name managed object property"
    ::= { cucsSwFcoeEstcEpEntry 10 }

cucsSwFcoeEstcEpPeerDn OBJECT-TYPE
    SYNTAX       SnmpAdminString
    MAX-ACCESS   read-only
    STATUS       current
    DESCRIPTION
        "Cisco UCS sw:FcoeEstcEp:peerDn managed object property"
    ::= { cucsSwFcoeEstcEpEntry 11 }

cucsSwFcoeEstcEpPeerPortId OBJECT-TYPE
    SYNTAX       Gauge32
    MAX-ACCESS   read-only
    STATUS       current
    DESCRIPTION
        "Cisco UCS sw:FcoeEstcEp:peerPortId managed object property"
    ::= { cucsSwFcoeEstcEpEntry 12 }

cucsSwFcoeEstcEpPeerSlotId OBJECT-TYPE
    SYNTAX       Gauge32
    MAX-ACCESS   read-only
    STATUS       current
    DESCRIPTION
        "Cisco UCS sw:FcoeEstcEp:peerSlotId managed object property"
    ::= { cucsSwFcoeEstcEpEntry 13 }

cucsSwFcoeEstcEpPortId OBJECT-TYPE
    SYNTAX       Gauge32
    MAX-ACCESS   read-only
    STATUS       current
    DESCRIPTION
        "Cisco UCS sw:FcoeEstcEp:portId managed object property"
    ::= { cucsSwFcoeEstcEpEntry 14 }

cucsSwFcoeEstcEpSlotId OBJECT-TYPE
    SYNTAX       Gauge32
    MAX-ACCESS   read-only
    STATUS       current
    DESCRIPTION
        "Cisco UCS sw:FcoeEstcEp:slotId managed object property"
    ::= { cucsSwFcoeEstcEpEntry 15 }

cucsSwFcoeEstcEpSwitchId OBJECT-TYPE
    SYNTAX       CucsNetworkSwitchId
    MAX-ACCESS   read-only
    STATUS       current
    DESCRIPTION
        "Cisco UCS sw:FcoeEstcEp:switchId managed object property"
    ::= { cucsSwFcoeEstcEpEntry 16 }

cucsSwFcoeEstcEpTransport OBJECT-TYPE
    SYNTAX       CucsSwFcoeEstcEpTransport
    MAX-ACCESS   read-only
    STATUS       current
    DESCRIPTION
        "Cisco UCS sw:FcoeEstcEp:transport managed object property"
    ::= { cucsSwFcoeEstcEpEntry 17 }

cucsSwFcoeEstcEpType OBJECT-TYPE
    SYNTAX       CucsNetworkConnectionType
    MAX-ACCESS   read-only
    STATUS       current
    DESCRIPTION
        "Cisco UCS sw:FcoeEstcEp:type managed object property"
    ::= { cucsSwFcoeEstcEpEntry 18 }

cucsSwFcoeEstcEpPeerChassisId OBJECT-TYPE
    SYNTAX       Gauge32
    MAX-ACCESS   read-only
    STATUS       current
    DESCRIPTION
        "Cisco UCS sw:FcoeEstcEp:peerChassisId managed object property"
    ::= { cucsSwFcoeEstcEpEntry 19 }

cucsSwFcoeEstcEpLc OBJECT-TYPE
    SYNTAX       CucsSwPIoEpLc
    MAX-ACCESS   read-only
    STATUS       current
    DESCRIPTION
        "Cisco UCS sw:FcoeEstcEp:lc managed object property"
    ::= { cucsSwFcoeEstcEpEntry 20 }

cucsSwPhysTable OBJECT-TYPE
    SYNTAX           SEQUENCE OF CucsSwPhysEntry
    MAX-ACCESS       not-accessible
    STATUS           current
    DESCRIPTION
        "Cisco UCS sw:Phys managed object table"
    ::= { cucsSwObjects 38 }

cucsSwPhysEntry OBJECT-TYPE
    SYNTAX           CucsSwPhysEntry
    MAX-ACCESS       not-accessible
    STATUS           current
    DESCRIPTION
        "Entry for the cucsSwPhysTable table."
    INDEX { cucsSwPhysInstanceId }
    ::= { cucsSwPhysTable 1 }

CucsSwPhysEntry ::= SEQUENCE {
    cucsSwPhysInstanceId                                             CucsManagedObjectId,
    cucsSwPhysDn                                                     CucsManagedObjectDn,
    cucsSwPhysRn                                                     SnmpAdminString,
    cucsSwPhysConfMode                                               CucsSwConfMode,
    cucsSwPhysFsmDescr                                               SnmpAdminString,
    cucsSwPhysFsmPrev                                                SnmpAdminString,
    cucsSwPhysFsmProgr                                               Gauge32,
    cucsSwPhysFsmRmtInvErrCode                                       Gauge32,
    cucsSwPhysFsmRmtInvErrDescr                                      SnmpAdminString,
    cucsSwPhysFsmRmtInvRslt                                          CucsConditionRemoteInvRslt,
    cucsSwPhysFsmStageDescr                                          SnmpAdminString,
    cucsSwPhysFsmStamp                                               DateAndTime,
    cucsSwPhysFsmStatus                                              SnmpAdminString,
    cucsSwPhysFsmTry                                                 Gauge32
}

cucsSwPhysInstanceId OBJECT-TYPE
    SYNTAX       CucsManagedObjectId
    MAX-ACCESS   not-accessible
    STATUS       current
    DESCRIPTION
        "Instance identifier of the managed object."
    ::= { cucsSwPhysEntry 1 }

cucsSwPhysDn OBJECT-TYPE
    SYNTAX       CucsManagedObjectDn
    MAX-ACCESS   read-only
    STATUS       current
    DESCRIPTION
        "Cisco UCS sw:Phys:dn managed object property"
    ::= { cucsSwPhysEntry 2 }

cucsSwPhysRn OBJECT-TYPE
    SYNTAX       SnmpAdminString
    MAX-ACCESS   read-only
    STATUS       current
    DESCRIPTION
        "Cisco UCS sw:Phys:rn managed object property"
    ::= { cucsSwPhysEntry 3 }

cucsSwPhysConfMode OBJECT-TYPE
    SYNTAX       CucsSwConfMode
    MAX-ACCESS   read-only
    STATUS       current
    DESCRIPTION
        "Cisco UCS sw:Phys:confMode managed object property"
    ::= { cucsSwPhysEntry 4 }

cucsSwPhysFsmDescr OBJECT-TYPE
    SYNTAX       SnmpAdminString
    MAX-ACCESS   read-only
    STATUS       current
    DESCRIPTION
        "Cisco UCS sw:Phys:fsmDescr managed object property"
    ::= { cucsSwPhysEntry 5 }

cucsSwPhysFsmPrev OBJECT-TYPE
    SYNTAX       SnmpAdminString
    MAX-ACCESS   read-only
    STATUS       current
    DESCRIPTION
        "Cisco UCS sw:Phys:fsmPrev managed object property"
    ::= { cucsSwPhysEntry 6 }

cucsSwPhysFsmProgr OBJECT-TYPE
    SYNTAX       Gauge32
    MAX-ACCESS   read-only
    STATUS       current
    DESCRIPTION
        "Cisco UCS sw:Phys:fsmProgr managed object property"
    ::= { cucsSwPhysEntry 7 }

cucsSwPhysFsmRmtInvErrCode OBJECT-TYPE
    SYNTAX       Gauge32
    MAX-ACCESS   read-only
    STATUS       current
    DESCRIPTION
        "Cisco UCS sw:Phys:fsmRmtInvErrCode managed object property"
    ::= { cucsSwPhysEntry 8 }

cucsSwPhysFsmRmtInvErrDescr OBJECT-TYPE
    SYNTAX       SnmpAdminString
    MAX-ACCESS   read-only
    STATUS       current
    DESCRIPTION
        "Cisco UCS sw:Phys:fsmRmtInvErrDescr managed object property"
    ::= { cucsSwPhysEntry 9 }

cucsSwPhysFsmRmtInvRslt OBJECT-TYPE
    SYNTAX       CucsConditionRemoteInvRslt
    MAX-ACCESS   read-only
    STATUS       current
    DESCRIPTION
        "Cisco UCS sw:Phys:fsmRmtInvRslt managed object property"
    ::= { cucsSwPhysEntry 10 }

cucsSwPhysFsmStageDescr OBJECT-TYPE
    SYNTAX       SnmpAdminString
    MAX-ACCESS   read-only
    STATUS       current
    DESCRIPTION
        "Cisco UCS sw:Phys:fsmStageDescr managed object property"
    ::= { cucsSwPhysEntry 11 }

cucsSwPhysFsmStamp OBJECT-TYPE
    SYNTAX       DateAndTime
    MAX-ACCESS   read-only
    STATUS       current
    DESCRIPTION
        "Cisco UCS sw:Phys:fsmStamp managed object property"
    ::= { cucsSwPhysEntry 12 }

cucsSwPhysFsmStatus OBJECT-TYPE
    SYNTAX       SnmpAdminString
    MAX-ACCESS   read-only
    STATUS       current
    DESCRIPTION
        "Cisco UCS sw:Phys:fsmStatus managed object property"
    ::= { cucsSwPhysEntry 13 }

cucsSwPhysFsmTry OBJECT-TYPE
    SYNTAX       Gauge32
    MAX-ACCESS   read-only
    STATUS       current
    DESCRIPTION
        "Cisco UCS sw:Phys:fsmTry managed object property"
    ::= { cucsSwPhysEntry 14 }

cucsSwPhysEtherEpTable OBJECT-TYPE
    SYNTAX           SEQUENCE OF CucsSwPhysEtherEpEntry
    MAX-ACCESS       not-accessible
    STATUS           current
    DESCRIPTION
        "Cisco UCS sw:PhysEtherEp managed object table"
    ::= { cucsSwObjects 39 }

cucsSwPhysEtherEpEntry OBJECT-TYPE
    SYNTAX           CucsSwPhysEtherEpEntry
    MAX-ACCESS       not-accessible
    STATUS           current
    DESCRIPTION
        "Entry for the cucsSwPhysEtherEpTable table."
    INDEX { cucsSwPhysEtherEpInstanceId }
    ::= { cucsSwPhysEtherEpTable 1 }

CucsSwPhysEtherEpEntry ::= SEQUENCE {
    cucsSwPhysEtherEpInstanceId                                      CucsManagedObjectId,
    cucsSwPhysEtherEpDn                                              CucsManagedObjectDn,
    cucsSwPhysEtherEpRn                                              SnmpAdminString,
    cucsSwPhysEtherEpAdminState                                      CucsFabricAdminState,
    cucsSwPhysEtherEpChassisId                                       Gauge32,
    cucsSwPhysEtherEpEpDn                                            SnmpAdminString,
    cucsSwPhysEtherEpIfRole                                          CucsNetworkPortRole,
    cucsSwPhysEtherEpIfType                                          CucsSwPIoEpIfType,
    cucsSwPhysEtherEpLc                                              CucsSwPIoEpLc,
    cucsSwPhysEtherEpLocale                                          CucsNetworkLocale,
    cucsSwPhysEtherEpName                                            SnmpAdminString,
    cucsSwPhysEtherEpPeerChassisId                                   Gauge32,
    cucsSwPhysEtherEpPeerDn                                          SnmpAdminString,
    cucsSwPhysEtherEpPeerPortId                                      Gauge32,
    cucsSwPhysEtherEpPeerSlotId                                      Gauge32,
    cucsSwPhysEtherEpPortId                                          Gauge32,
    cucsSwPhysEtherEpSlotId                                          Gauge32,
    cucsSwPhysEtherEpSwitchId                                        CucsNetworkSwitchId,
    cucsSwPhysEtherEpTransport                                       CucsNetworkTransport,
    cucsSwPhysEtherEpType                                            CucsNetworkConnectionType
}

cucsSwPhysEtherEpInstanceId OBJECT-TYPE
    SYNTAX       CucsManagedObjectId
    MAX-ACCESS   not-accessible
    STATUS       current
    DESCRIPTION
        "Instance identifier of the managed object."
    ::= { cucsSwPhysEtherEpEntry 1 }

cucsSwPhysEtherEpDn OBJECT-TYPE
    SYNTAX       CucsManagedObjectDn
    MAX-ACCESS   read-only
    STATUS       current
    DESCRIPTION
        "Cisco UCS sw:PhysEtherEp:dn managed object property"
    ::= { cucsSwPhysEtherEpEntry 2 }

cucsSwPhysEtherEpRn OBJECT-TYPE
    SYNTAX       SnmpAdminString
    MAX-ACCESS   read-only
    STATUS       current
    DESCRIPTION
        "Cisco UCS sw:PhysEtherEp:rn managed object property"
    ::= { cucsSwPhysEtherEpEntry 3 }

cucsSwPhysEtherEpAdminState OBJECT-TYPE
    SYNTAX       CucsFabricAdminState
    MAX-ACCESS   read-only
    STATUS       current
    DESCRIPTION
        "Cisco UCS sw:PhysEtherEp:adminState managed object property"
    ::= { cucsSwPhysEtherEpEntry 4 }

cucsSwPhysEtherEpChassisId OBJECT-TYPE
    SYNTAX       Gauge32
    MAX-ACCESS   read-only
    STATUS       current
    DESCRIPTION
        "Cisco UCS sw:PhysEtherEp:chassisId managed object property"
    ::= { cucsSwPhysEtherEpEntry 5 }

cucsSwPhysEtherEpEpDn OBJECT-TYPE
    SYNTAX       SnmpAdminString
    MAX-ACCESS   read-only
    STATUS       current
    DESCRIPTION
        "Cisco UCS sw:PhysEtherEp:epDn managed object property"
    ::= { cucsSwPhysEtherEpEntry 6 }

cucsSwPhysEtherEpIfRole OBJECT-TYPE
    SYNTAX       CucsNetworkPortRole
    MAX-ACCESS   read-only
    STATUS       current
    DESCRIPTION
        "Cisco UCS sw:PhysEtherEp:ifRole managed object property"
    ::= { cucsSwPhysEtherEpEntry 7 }

cucsSwPhysEtherEpIfType OBJECT-TYPE
    SYNTAX       CucsSwPIoEpIfType
    MAX-ACCESS   read-only
    STATUS       current
    DESCRIPTION
        "Cisco UCS sw:PhysEtherEp:ifType managed object property"
    ::= { cucsSwPhysEtherEpEntry 8 }

cucsSwPhysEtherEpLc OBJECT-TYPE
    SYNTAX       CucsSwPIoEpLc
    MAX-ACCESS   read-only
    STATUS       current
    DESCRIPTION
        "Cisco UCS sw:PhysEtherEp:lc managed object property"
    ::= { cucsSwPhysEtherEpEntry 9 }

cucsSwPhysEtherEpLocale OBJECT-TYPE
    SYNTAX       CucsNetworkLocale
    MAX-ACCESS   read-only
    STATUS       current
    DESCRIPTION
        "Cisco UCS sw:PhysEtherEp:locale managed object property"
    ::= { cucsSwPhysEtherEpEntry 10 }

cucsSwPhysEtherEpName OBJECT-TYPE
    SYNTAX       SnmpAdminString
    MAX-ACCESS   read-only
    STATUS       current
    DESCRIPTION
        "Cisco UCS sw:PhysEtherEp:name managed object property"
    ::= { cucsSwPhysEtherEpEntry 11 }

cucsSwPhysEtherEpPeerChassisId OBJECT-TYPE
    SYNTAX       Gauge32
    MAX-ACCESS   read-only
    STATUS       current
    DESCRIPTION
        "Cisco UCS sw:PhysEtherEp:peerChassisId managed object property"
    ::= { cucsSwPhysEtherEpEntry 12 }

cucsSwPhysEtherEpPeerDn OBJECT-TYPE
    SYNTAX       SnmpAdminString
    MAX-ACCESS   read-only
    STATUS       current
    DESCRIPTION
        "Cisco UCS sw:PhysEtherEp:peerDn managed object property"
    ::= { cucsSwPhysEtherEpEntry 13 }

cucsSwPhysEtherEpPeerPortId OBJECT-TYPE
    SYNTAX       Gauge32
    MAX-ACCESS   read-only
    STATUS       current
    DESCRIPTION
        "Cisco UCS sw:PhysEtherEp:peerPortId managed object property"
    ::= { cucsSwPhysEtherEpEntry 14 }

cucsSwPhysEtherEpPeerSlotId OBJECT-TYPE
    SYNTAX       Gauge32
    MAX-ACCESS   read-only
    STATUS       current
    DESCRIPTION
        "Cisco UCS sw:PhysEtherEp:peerSlotId managed object property"
    ::= { cucsSwPhysEtherEpEntry 15 }

cucsSwPhysEtherEpPortId OBJECT-TYPE
    SYNTAX       Gauge32
    MAX-ACCESS   read-only
    STATUS       current
    DESCRIPTION
        "Cisco UCS sw:PhysEtherEp:portId managed object property"
    ::= { cucsSwPhysEtherEpEntry 16 }

cucsSwPhysEtherEpSlotId OBJECT-TYPE
    SYNTAX       Gauge32
    MAX-ACCESS   read-only
    STATUS       current
    DESCRIPTION
        "Cisco UCS sw:PhysEtherEp:slotId managed object property"
    ::= { cucsSwPhysEtherEpEntry 17 }

cucsSwPhysEtherEpSwitchId OBJECT-TYPE
    SYNTAX       CucsNetworkSwitchId
    MAX-ACCESS   read-only
    STATUS       current
    DESCRIPTION
        "Cisco UCS sw:PhysEtherEp:switchId managed object property"
    ::= { cucsSwPhysEtherEpEntry 18 }

cucsSwPhysEtherEpTransport OBJECT-TYPE
    SYNTAX       CucsNetworkTransport
    MAX-ACCESS   read-only
    STATUS       current
    DESCRIPTION
        "Cisco UCS sw:PhysEtherEp:transport managed object property"
    ::= { cucsSwPhysEtherEpEntry 19 }

cucsSwPhysEtherEpType OBJECT-TYPE
    SYNTAX       CucsNetworkConnectionType
    MAX-ACCESS   read-only
    STATUS       current
    DESCRIPTION
        "Cisco UCS sw:PhysEtherEp:type managed object property"
    ::= { cucsSwPhysEtherEpEntry 20 }

cucsSwPhysFcEpTable OBJECT-TYPE
    SYNTAX           SEQUENCE OF CucsSwPhysFcEpEntry
    MAX-ACCESS       not-accessible
    STATUS           current
    DESCRIPTION
        "Cisco UCS sw:PhysFcEp managed object table"
    ::= { cucsSwObjects 40 }

cucsSwPhysFcEpEntry OBJECT-TYPE
    SYNTAX           CucsSwPhysFcEpEntry
    MAX-ACCESS       not-accessible
    STATUS           current
    DESCRIPTION
        "Entry for the cucsSwPhysFcEpTable table."
    INDEX { cucsSwPhysFcEpInstanceId }
    ::= { cucsSwPhysFcEpTable 1 }

CucsSwPhysFcEpEntry ::= SEQUENCE {
    cucsSwPhysFcEpInstanceId                                         CucsManagedObjectId,
    cucsSwPhysFcEpDn                                                 CucsManagedObjectDn,
    cucsSwPhysFcEpRn                                                 SnmpAdminString,
    cucsSwPhysFcEpAdminState                                         CucsFabricAdminState,
    cucsSwPhysFcEpChassisId                                          Gauge32,
    cucsSwPhysFcEpEpDn                                               SnmpAdminString,
    cucsSwPhysFcEpIfRole                                             CucsNetworkPortRole,
    cucsSwPhysFcEpIfType                                             CucsSwPIoEpIfType,
    cucsSwPhysFcEpLc                                                 CucsSwPIoEpLc,
    cucsSwPhysFcEpLocale                                             CucsNetworkLocale,
    cucsSwPhysFcEpName                                               SnmpAdminString,
    cucsSwPhysFcEpPeerChassisId                                      Gauge32,
    cucsSwPhysFcEpPeerDn                                             SnmpAdminString,
    cucsSwPhysFcEpPeerPortId                                         Gauge32,
    cucsSwPhysFcEpPeerSlotId                                         Gauge32,
    cucsSwPhysFcEpPortId                                             Gauge32,
    cucsSwPhysFcEpSlotId                                             Gauge32,
    cucsSwPhysFcEpSwitchId                                           CucsNetworkSwitchId,
    cucsSwPhysFcEpTransport                                          CucsNetworkTransport,
    cucsSwPhysFcEpType                                               CucsNetworkConnectionType
}

cucsSwPhysFcEpInstanceId OBJECT-TYPE
    SYNTAX       CucsManagedObjectId
    MAX-ACCESS   not-accessible
    STATUS       current
    DESCRIPTION
        "Instance identifier of the managed object."
    ::= { cucsSwPhysFcEpEntry 1 }

cucsSwPhysFcEpDn OBJECT-TYPE
    SYNTAX       CucsManagedObjectDn
    MAX-ACCESS   read-only
    STATUS       current
    DESCRIPTION
        "Cisco UCS sw:PhysFcEp:dn managed object property"
    ::= { cucsSwPhysFcEpEntry 2 }

cucsSwPhysFcEpRn OBJECT-TYPE
    SYNTAX       SnmpAdminString
    MAX-ACCESS   read-only
    STATUS       current
    DESCRIPTION
        "Cisco UCS sw:PhysFcEp:rn managed object property"
    ::= { cucsSwPhysFcEpEntry 3 }

cucsSwPhysFcEpAdminState OBJECT-TYPE
    SYNTAX       CucsFabricAdminState
    MAX-ACCESS   read-only
    STATUS       current
    DESCRIPTION
        "Cisco UCS sw:PhysFcEp:adminState managed object property"
    ::= { cucsSwPhysFcEpEntry 4 }

cucsSwPhysFcEpChassisId OBJECT-TYPE
    SYNTAX       Gauge32
    MAX-ACCESS   read-only
    STATUS       current
    DESCRIPTION
        "Cisco UCS sw:PhysFcEp:chassisId managed object property"
    ::= { cucsSwPhysFcEpEntry 5 }

cucsSwPhysFcEpEpDn OBJECT-TYPE
    SYNTAX       SnmpAdminString
    MAX-ACCESS   read-only
    STATUS       current
    DESCRIPTION
        "Cisco UCS sw:PhysFcEp:epDn managed object property"
    ::= { cucsSwPhysFcEpEntry 6 }

cucsSwPhysFcEpIfRole OBJECT-TYPE
    SYNTAX       CucsNetworkPortRole
    MAX-ACCESS   read-only
    STATUS       current
    DESCRIPTION
        "Cisco UCS sw:PhysFcEp:ifRole managed object property"
    ::= { cucsSwPhysFcEpEntry 7 }

cucsSwPhysFcEpIfType OBJECT-TYPE
    SYNTAX       CucsSwPIoEpIfType
    MAX-ACCESS   read-only
    STATUS       current
    DESCRIPTION
        "Cisco UCS sw:PhysFcEp:ifType managed object property"
    ::= { cucsSwPhysFcEpEntry 8 }

cucsSwPhysFcEpLc OBJECT-TYPE
    SYNTAX       CucsSwPIoEpLc
    MAX-ACCESS   read-only
    STATUS       current
    DESCRIPTION
        "Cisco UCS sw:PhysFcEp:lc managed object property"
    ::= { cucsSwPhysFcEpEntry 9 }

cucsSwPhysFcEpLocale OBJECT-TYPE
    SYNTAX       CucsNetworkLocale
    MAX-ACCESS   read-only
    STATUS       current
    DESCRIPTION
        "Cisco UCS sw:PhysFcEp:locale managed object property"
    ::= { cucsSwPhysFcEpEntry 10 }

cucsSwPhysFcEpName OBJECT-TYPE
    SYNTAX       SnmpAdminString
    MAX-ACCESS   read-only
    STATUS       current
    DESCRIPTION
        "Cisco UCS sw:PhysFcEp:name managed object property"
    ::= { cucsSwPhysFcEpEntry 11 }

cucsSwPhysFcEpPeerChassisId OBJECT-TYPE
    SYNTAX       Gauge32
    MAX-ACCESS   read-only
    STATUS       current
    DESCRIPTION
        "Cisco UCS sw:PhysFcEp:peerChassisId managed object property"
    ::= { cucsSwPhysFcEpEntry 12 }

cucsSwPhysFcEpPeerDn OBJECT-TYPE
    SYNTAX       SnmpAdminString
    MAX-ACCESS   read-only
    STATUS       current
    DESCRIPTION
        "Cisco UCS sw:PhysFcEp:peerDn managed object property"
    ::= { cucsSwPhysFcEpEntry 13 }

cucsSwPhysFcEpPeerPortId OBJECT-TYPE
    SYNTAX       Gauge32
    MAX-ACCESS   read-only
    STATUS       current
    DESCRIPTION
        "Cisco UCS sw:PhysFcEp:peerPortId managed object property"
    ::= { cucsSwPhysFcEpEntry 14 }

cucsSwPhysFcEpPeerSlotId OBJECT-TYPE
    SYNTAX       Gauge32
    MAX-ACCESS   read-only
    STATUS       current
    DESCRIPTION
        "Cisco UCS sw:PhysFcEp:peerSlotId managed object property"
    ::= { cucsSwPhysFcEpEntry 15 }

cucsSwPhysFcEpPortId OBJECT-TYPE
    SYNTAX       Gauge32
    MAX-ACCESS   read-only
    STATUS       current
    DESCRIPTION
        "Cisco UCS sw:PhysFcEp:portId managed object property"
    ::= { cucsSwPhysFcEpEntry 16 }

cucsSwPhysFcEpSlotId OBJECT-TYPE
    SYNTAX       Gauge32
    MAX-ACCESS   read-only
    STATUS       current
    DESCRIPTION
        "Cisco UCS sw:PhysFcEp:slotId managed object property"
    ::= { cucsSwPhysFcEpEntry 17 }

cucsSwPhysFcEpSwitchId OBJECT-TYPE
    SYNTAX       CucsNetworkSwitchId
    MAX-ACCESS   read-only
    STATUS       current
    DESCRIPTION
        "Cisco UCS sw:PhysFcEp:switchId managed object property"
    ::= { cucsSwPhysFcEpEntry 18 }

cucsSwPhysFcEpTransport OBJECT-TYPE
    SYNTAX       CucsNetworkTransport
    MAX-ACCESS   read-only
    STATUS       current
    DESCRIPTION
        "Cisco UCS sw:PhysFcEp:transport managed object property"
    ::= { cucsSwPhysFcEpEntry 19 }

cucsSwPhysFcEpType OBJECT-TYPE
    SYNTAX       CucsNetworkConnectionType
    MAX-ACCESS   read-only
    STATUS       current
    DESCRIPTION
        "Cisco UCS sw:PhysFcEp:type managed object property"
    ::= { cucsSwPhysFcEpEntry 20 }

cucsSwPhysFsmTaskTable OBJECT-TYPE
    SYNTAX           SEQUENCE OF CucsSwPhysFsmTaskEntry
    MAX-ACCESS       not-accessible
    STATUS           current
    DESCRIPTION
        "Cisco UCS sw:PhysFsmTask managed object table"
    ::= { cucsSwObjects 41 }

cucsSwPhysFsmTaskEntry OBJECT-TYPE
    SYNTAX           CucsSwPhysFsmTaskEntry
    MAX-ACCESS       not-accessible
    STATUS           current
    DESCRIPTION
        "Entry for the cucsSwPhysFsmTaskTable table."
    INDEX { cucsSwPhysFsmTaskInstanceId }
    ::= { cucsSwPhysFsmTaskTable 1 }

CucsSwPhysFsmTaskEntry ::= SEQUENCE {
    cucsSwPhysFsmTaskInstanceId                                      CucsManagedObjectId,
    cucsSwPhysFsmTaskDn                                              CucsManagedObjectDn,
    cucsSwPhysFsmTaskRn                                              SnmpAdminString,
    cucsSwPhysFsmTaskCompletion                                      CucsFsmCompletion,
    cucsSwPhysFsmTaskFlags                                           CucsFsmFlags,
    cucsSwPhysFsmTaskItem                                            CucsSwPhysFsmTaskItem,
    cucsSwPhysFsmTaskSeqId                                           Gauge32
}

cucsSwPhysFsmTaskInstanceId OBJECT-TYPE
    SYNTAX       CucsManagedObjectId
    MAX-ACCESS   not-accessible
    STATUS       current
    DESCRIPTION
        "Instance identifier of the managed object."
    ::= { cucsSwPhysFsmTaskEntry 1 }

cucsSwPhysFsmTaskDn OBJECT-TYPE
    SYNTAX       CucsManagedObjectDn
    MAX-ACCESS   read-only
    STATUS       current
    DESCRIPTION
        "Cisco UCS sw:PhysFsmTask:dn managed object property"
    ::= { cucsSwPhysFsmTaskEntry 2 }

cucsSwPhysFsmTaskRn OBJECT-TYPE
    SYNTAX       SnmpAdminString
    MAX-ACCESS   read-only
    STATUS       current
    DESCRIPTION
        "Cisco UCS sw:PhysFsmTask:rn managed object property"
    ::= { cucsSwPhysFsmTaskEntry 3 }

cucsSwPhysFsmTaskCompletion OBJECT-TYPE
    SYNTAX       CucsFsmCompletion
    MAX-ACCESS   read-only
    STATUS       current
    DESCRIPTION
        "Cisco UCS sw:PhysFsmTask:completion managed object property"
    ::= { cucsSwPhysFsmTaskEntry 4 }

cucsSwPhysFsmTaskFlags OBJECT-TYPE
    SYNTAX       CucsFsmFlags
    MAX-ACCESS   read-only
    STATUS       current
    DESCRIPTION
        "Cisco UCS sw:PhysFsmTask:flags managed object property"
    ::= { cucsSwPhysFsmTaskEntry 5 }

cucsSwPhysFsmTaskItem OBJECT-TYPE
    SYNTAX       CucsSwPhysFsmTaskItem
    MAX-ACCESS   read-only
    STATUS       current
    DESCRIPTION
        "Cisco UCS sw:PhysFsmTask:item managed object property"
    ::= { cucsSwPhysFsmTaskEntry 6 }

cucsSwPhysFsmTaskSeqId OBJECT-TYPE
    SYNTAX       Gauge32
    MAX-ACCESS   read-only
    STATUS       current
    DESCRIPTION
        "Cisco UCS sw:PhysFsmTask:seqId managed object property"
    ::= { cucsSwPhysFsmTaskEntry 7 }

cucsSwSystemStatsTable OBJECT-TYPE
    SYNTAX           SEQUENCE OF CucsSwSystemStatsEntry
    MAX-ACCESS       not-accessible
    STATUS           current
    DESCRIPTION
        "Cisco UCS sw:SystemStats managed object table"
    ::= { cucsSwObjects 28 }

cucsSwSystemStatsEntry OBJECT-TYPE
    SYNTAX           CucsSwSystemStatsEntry
    MAX-ACCESS       not-accessible
    STATUS           current
    DESCRIPTION
        "Entry for the cucsSwSystemStatsTable table."
    INDEX { cucsSwSystemStatsInstanceId }
    ::= { cucsSwSystemStatsTable 1 }

CucsSwSystemStatsEntry ::= SEQUENCE {
    cucsSwSystemStatsInstanceId                                      CucsManagedObjectId,
    cucsSwSystemStatsDn                                              CucsManagedObjectDn,
    cucsSwSystemStatsRn                                              SnmpAdminString,
    cucsSwSystemStatsIntervals                                       Gauge32,
    cucsSwSystemStatsLoad                                            INTEGER,
    cucsSwSystemStatsLoadAvg                                         INTEGER,
    cucsSwSystemStatsLoadMax                                         INTEGER,
    cucsSwSystemStatsLoadMin                                         INTEGER,
    cucsSwSystemStatsMemAvailable                                    Gauge32,
    cucsSwSystemStatsMemAvailableAvg                                 Gauge32,
    cucsSwSystemStatsMemAvailableMax                                 Gauge32,
    cucsSwSystemStatsMemAvailableMin                                 Gauge32,
    cucsSwSystemStatsMemCached                                       Gauge32,
    cucsSwSystemStatsMemCachedAvg                                    Gauge32,
    cucsSwSystemStatsMemCachedMax                                    Gauge32,
    cucsSwSystemStatsMemCachedMin                                    Gauge32,
    cucsSwSystemStatsSuspect                                         TruthValue,
    cucsSwSystemStatsThresholded                                     CucsSwSystemStatsThresholded,
    cucsSwSystemStatsTimeCollected                                   DateAndTime,
    cucsSwSystemStatsUpdate                                          Gauge32
}

cucsSwSystemStatsInstanceId OBJECT-TYPE
    SYNTAX       CucsManagedObjectId
    MAX-ACCESS   not-accessible
    STATUS       current
    DESCRIPTION
        "Instance identifier of the managed object."
    ::= { cucsSwSystemStatsEntry 1 }

cucsSwSystemStatsDn OBJECT-TYPE
    SYNTAX       CucsManagedObjectDn
    MAX-ACCESS   read-only
    STATUS       current
    DESCRIPTION
        "Cisco UCS sw:SystemStats:dn managed object property"
    ::= { cucsSwSystemStatsEntry 2 }

cucsSwSystemStatsRn OBJECT-TYPE
    SYNTAX       SnmpAdminString
    MAX-ACCESS   read-only
    STATUS       current
    DESCRIPTION
        "Cisco UCS sw:SystemStats:rn managed object property"
    ::= { cucsSwSystemStatsEntry 3 }

cucsSwSystemStatsIntervals OBJECT-TYPE
    SYNTAX       Gauge32
    MAX-ACCESS   read-only
    STATUS       current
    DESCRIPTION
        "Cisco UCS sw:SystemStats:intervals managed object property"
    ::= { cucsSwSystemStatsEntry 4 }

cucsSwSystemStatsLoad OBJECT-TYPE
    SYNTAX       INTEGER
    MAX-ACCESS   read-only
    STATUS       current
    DESCRIPTION
        "Cisco UCS sw:SystemStats:load managed object property"
    ::= { cucsSwSystemStatsEntry 5 }

cucsSwSystemStatsLoadAvg OBJECT-TYPE
    SYNTAX       INTEGER
    MAX-ACCESS   read-only
    STATUS       current
    DESCRIPTION
        "Cisco UCS sw:SystemStats:loadAvg managed object property"
    ::= { cucsSwSystemStatsEntry 6 }

cucsSwSystemStatsLoadMax OBJECT-TYPE
    SYNTAX       INTEGER
    MAX-ACCESS   read-only
    STATUS       current
    DESCRIPTION
        "Cisco UCS sw:SystemStats:loadMax managed object property"
    ::= { cucsSwSystemStatsEntry 7 }

cucsSwSystemStatsLoadMin OBJECT-TYPE
    SYNTAX       INTEGER
    MAX-ACCESS   read-only
    STATUS       current
    DESCRIPTION
        "Cisco UCS sw:SystemStats:loadMin managed object property"
    ::= { cucsSwSystemStatsEntry 8 }

cucsSwSystemStatsMemAvailable OBJECT-TYPE
    SYNTAX       Gauge32
    MAX-ACCESS   read-only
    STATUS       current
    DESCRIPTION
        "Cisco UCS sw:SystemStats:memAvailable managed object property"
    ::= { cucsSwSystemStatsEntry 9 }

cucsSwSystemStatsMemAvailableAvg OBJECT-TYPE
    SYNTAX       Gauge32
    MAX-ACCESS   read-only
    STATUS       current
    DESCRIPTION
        "Cisco UCS sw:SystemStats:memAvailableAvg managed object property"
    ::= { cucsSwSystemStatsEntry 10 }

cucsSwSystemStatsMemAvailableMax OBJECT-TYPE
    SYNTAX       Gauge32
    MAX-ACCESS   read-only
    STATUS       current
    DESCRIPTION
        "Cisco UCS sw:SystemStats:memAvailableMax managed object property"
    ::= { cucsSwSystemStatsEntry 11 }

cucsSwSystemStatsMemAvailableMin OBJECT-TYPE
    SYNTAX       Gauge32
    MAX-ACCESS   read-only
    STATUS       current
    DESCRIPTION
        "Cisco UCS sw:SystemStats:memAvailableMin managed object property"
    ::= { cucsSwSystemStatsEntry 12 }

cucsSwSystemStatsMemCached OBJECT-TYPE
    SYNTAX       Gauge32
    MAX-ACCESS   read-only
    STATUS       current
    DESCRIPTION
        "Cisco UCS sw:SystemStats:memCached managed object property"
    ::= { cucsSwSystemStatsEntry 13 }

cucsSwSystemStatsMemCachedAvg OBJECT-TYPE
    SYNTAX       Gauge32
    MAX-ACCESS   read-only
    STATUS       current
    DESCRIPTION
        "Cisco UCS sw:SystemStats:memCachedAvg managed object property"
    ::= { cucsSwSystemStatsEntry 14 }

cucsSwSystemStatsMemCachedMax OBJECT-TYPE
    SYNTAX       Gauge32
    MAX-ACCESS   read-only
    STATUS       current
    DESCRIPTION
        "Cisco UCS sw:SystemStats:memCachedMax managed object property"
    ::= { cucsSwSystemStatsEntry 15 }

cucsSwSystemStatsMemCachedMin OBJECT-TYPE
    SYNTAX       Gauge32
    MAX-ACCESS   read-only
    STATUS       current
    DESCRIPTION
        "Cisco UCS sw:SystemStats:memCachedMin managed object property"
    ::= { cucsSwSystemStatsEntry 16 }

cucsSwSystemStatsSuspect OBJECT-TYPE
    SYNTAX       TruthValue
    MAX-ACCESS   read-only
    STATUS       current
    DESCRIPTION
        "Cisco UCS sw:SystemStats:suspect managed object property"
    ::= { cucsSwSystemStatsEntry 17 }

cucsSwSystemStatsThresholded OBJECT-TYPE
    SYNTAX       CucsSwSystemStatsThresholded
    MAX-ACCESS   read-only
    STATUS       current
    DESCRIPTION
        "Cisco UCS sw:SystemStats:thresholded managed object property"
    ::= { cucsSwSystemStatsEntry 18 }

cucsSwSystemStatsTimeCollected OBJECT-TYPE
    SYNTAX       DateAndTime
    MAX-ACCESS   read-only
    STATUS       current
    DESCRIPTION
        "Cisco UCS sw:SystemStats:timeCollected managed object property"
    ::= { cucsSwSystemStatsEntry 19 }

cucsSwSystemStatsUpdate OBJECT-TYPE
    SYNTAX       Gauge32
    MAX-ACCESS   read-only
    STATUS       current
    DESCRIPTION
        "Cisco UCS sw:SystemStats:update managed object property"
    ::= { cucsSwSystemStatsEntry 20 }

cucsSwSystemStatsHistTable OBJECT-TYPE
    SYNTAX           SEQUENCE OF CucsSwSystemStatsHistEntry
    MAX-ACCESS       not-accessible
    STATUS           current
    DESCRIPTION
        "Cisco UCS sw:SystemStatsHist managed object table"
    ::= { cucsSwObjects 29 }

cucsSwSystemStatsHistEntry OBJECT-TYPE
    SYNTAX           CucsSwSystemStatsHistEntry
    MAX-ACCESS       not-accessible
    STATUS           current
    DESCRIPTION
        "Entry for the cucsSwSystemStatsHistTable table."
    INDEX { cucsSwSystemStatsHistInstanceId }
    ::= { cucsSwSystemStatsHistTable 1 }

CucsSwSystemStatsHistEntry ::= SEQUENCE {
    cucsSwSystemStatsHistInstanceId                                  CucsManagedObjectId,
    cucsSwSystemStatsHistDn                                          CucsManagedObjectDn,
    cucsSwSystemStatsHistRn                                          SnmpAdminString,
    cucsSwSystemStatsHistId                                          Unsigned64,
    cucsSwSystemStatsHistLoad                                        INTEGER,
    cucsSwSystemStatsHistLoadAvg                                     INTEGER,
    cucsSwSystemStatsHistLoadMax                                     INTEGER,
    cucsSwSystemStatsHistLoadMin                                     INTEGER,
    cucsSwSystemStatsHistMemAvailable                                Gauge32,
    cucsSwSystemStatsHistMemAvailableAvg                             Gauge32,
    cucsSwSystemStatsHistMemAvailableMax                             Gauge32,
    cucsSwSystemStatsHistMemAvailableMin                             Gauge32,
    cucsSwSystemStatsHistMemCached                                   Gauge32,
    cucsSwSystemStatsHistMemCachedAvg                                Gauge32,
    cucsSwSystemStatsHistMemCachedMax                                Gauge32,
    cucsSwSystemStatsHistMemCachedMin                                Gauge32,
    cucsSwSystemStatsHistMostRecent                                  TruthValue,
    cucsSwSystemStatsHistSuspect                                     TruthValue,
    cucsSwSystemStatsHistThresholded                                 CucsSwSystemStatsHistThresholded,
    cucsSwSystemStatsHistTimeCollected                               DateAndTime
}

cucsSwSystemStatsHistInstanceId OBJECT-TYPE
    SYNTAX       CucsManagedObjectId
    MAX-ACCESS   not-accessible
    STATUS       current
    DESCRIPTION
        "Instance identifier of the managed object."
    ::= { cucsSwSystemStatsHistEntry 1 }

cucsSwSystemStatsHistDn OBJECT-TYPE
    SYNTAX       CucsManagedObjectDn
    MAX-ACCESS   read-only
    STATUS       current
    DESCRIPTION
        "Cisco UCS sw:SystemStatsHist:dn managed object property"
    ::= { cucsSwSystemStatsHistEntry 2 }

cucsSwSystemStatsHistRn OBJECT-TYPE
    SYNTAX       SnmpAdminString
    MAX-ACCESS   read-only
    STATUS       current
    DESCRIPTION
        "Cisco UCS sw:SystemStatsHist:rn managed object property"
    ::= { cucsSwSystemStatsHistEntry 3 }

cucsSwSystemStatsHistId OBJECT-TYPE
    SYNTAX       Unsigned64
    MAX-ACCESS   read-only
    STATUS       current
    DESCRIPTION
        "Cisco UCS sw:SystemStatsHist:id managed object property"
    ::= { cucsSwSystemStatsHistEntry 4 }

cucsSwSystemStatsHistLoad OBJECT-TYPE
    SYNTAX       INTEGER
    MAX-ACCESS   read-only
    STATUS       current
    DESCRIPTION
        "Cisco UCS sw:SystemStatsHist:load managed object property"
    ::= { cucsSwSystemStatsHistEntry 5 }

cucsSwSystemStatsHistLoadAvg OBJECT-TYPE
    SYNTAX       INTEGER
    MAX-ACCESS   read-only
    STATUS       current
    DESCRIPTION
        "Cisco UCS sw:SystemStatsHist:loadAvg managed object property"
    ::= { cucsSwSystemStatsHistEntry 6 }

cucsSwSystemStatsHistLoadMax OBJECT-TYPE
    SYNTAX       INTEGER
    MAX-ACCESS   read-only
    STATUS       current
    DESCRIPTION
        "Cisco UCS sw:SystemStatsHist:loadMax managed object property"
    ::= { cucsSwSystemStatsHistEntry 7 }

cucsSwSystemStatsHistLoadMin OBJECT-TYPE
    SYNTAX       INTEGER
    MAX-ACCESS   read-only
    STATUS       current
    DESCRIPTION
        "Cisco UCS sw:SystemStatsHist:loadMin managed object property"
    ::= { cucsSwSystemStatsHistEntry 8 }

cucsSwSystemStatsHistMemAvailable OBJECT-TYPE
    SYNTAX       Gauge32
    MAX-ACCESS   read-only
    STATUS       current
    DESCRIPTION
        "Cisco UCS sw:SystemStatsHist:memAvailable managed
        object property"
    ::= { cucsSwSystemStatsHistEntry 9 }

cucsSwSystemStatsHistMemAvailableAvg OBJECT-TYPE
    SYNTAX       Gauge32
    MAX-ACCESS   read-only
    STATUS       current
    DESCRIPTION
        "Cisco UCS sw:SystemStatsHist:memAvailableAvg managed
        object property"
    ::= { cucsSwSystemStatsHistEntry 10 }

cucsSwSystemStatsHistMemAvailableMax OBJECT-TYPE
    SYNTAX       Gauge32
    MAX-ACCESS   read-only
    STATUS       current
    DESCRIPTION
        "Cisco UCS sw:SystemStatsHist:memAvailableMax managed
        object property"
    ::= { cucsSwSystemStatsHistEntry 11 }

cucsSwSystemStatsHistMemAvailableMin OBJECT-TYPE
    SYNTAX       Gauge32
    MAX-ACCESS   read-only
    STATUS       current
    DESCRIPTION
        "Cisco UCS sw:SystemStatsHist:memAvailableMin managed
        object property"
    ::= { cucsSwSystemStatsHistEntry 12 }

cucsSwSystemStatsHistMemCached OBJECT-TYPE
    SYNTAX       Gauge32
    MAX-ACCESS   read-only
    STATUS       current
    DESCRIPTION
        "Cisco UCS sw:SystemStatsHist:memCached managed object property"
    ::= { cucsSwSystemStatsHistEntry 13 }

cucsSwSystemStatsHistMemCachedAvg OBJECT-TYPE
    SYNTAX       Gauge32
    MAX-ACCESS   read-only
    STATUS       current
    DESCRIPTION
        "Cisco UCS sw:SystemStatsHist:memCachedAvg managed
        object property"
    ::= { cucsSwSystemStatsHistEntry 14 }

cucsSwSystemStatsHistMemCachedMax OBJECT-TYPE
    SYNTAX       Gauge32
    MAX-ACCESS   read-only
    STATUS       current
    DESCRIPTION
        "Cisco UCS sw:SystemStatsHist:memCachedMax managed
        object property"
    ::= { cucsSwSystemStatsHistEntry 15 }

cucsSwSystemStatsHistMemCachedMin OBJECT-TYPE
    SYNTAX       Gauge32
    MAX-ACCESS   read-only
    STATUS       current
    DESCRIPTION
        "Cisco UCS sw:SystemStatsHist:memCachedMin managed
        object property"
    ::= { cucsSwSystemStatsHistEntry 16 }

cucsSwSystemStatsHistMostRecent OBJECT-TYPE
    SYNTAX       TruthValue
    MAX-ACCESS   read-only
    STATUS       current
    DESCRIPTION
        "Cisco UCS sw:SystemStatsHist:mostRecent managed object property"
    ::= { cucsSwSystemStatsHistEntry 17 }

cucsSwSystemStatsHistSuspect OBJECT-TYPE
    SYNTAX       TruthValue
    MAX-ACCESS   read-only
    STATUS       current
    DESCRIPTION
        "Cisco UCS sw:SystemStatsHist:suspect managed object property"
    ::= { cucsSwSystemStatsHistEntry 18 }

cucsSwSystemStatsHistThresholded OBJECT-TYPE
    SYNTAX       CucsSwSystemStatsHistThresholded
    MAX-ACCESS   read-only
    STATUS       current
    DESCRIPTION
        "Cisco UCS sw:SystemStatsHist:thresholded managed object property"
    ::= { cucsSwSystemStatsHistEntry 19 }

cucsSwSystemStatsHistTimeCollected OBJECT-TYPE
    SYNTAX       DateAndTime
    MAX-ACCESS   read-only
    STATUS       current
    DESCRIPTION
        "Cisco UCS sw:SystemStatsHist:timeCollected managed
        object property"
    ::= { cucsSwSystemStatsHistEntry 20 }

cucsSwUlanTable OBJECT-TYPE
    SYNTAX           SEQUENCE OF CucsSwUlanEntry
    MAX-ACCESS       not-accessible
    STATUS           current
    DESCRIPTION
        "Cisco UCS sw:Ulan managed object table"
    ::= { cucsSwObjects 30 }

cucsSwUlanEntry OBJECT-TYPE
    SYNTAX           CucsSwUlanEntry
    MAX-ACCESS       not-accessible
    STATUS           current
    DESCRIPTION
        "Entry for the cucsSwUlanTable table."
    INDEX { cucsSwUlanInstanceId }
    ::= { cucsSwUlanTable 1 }

CucsSwUlanEntry ::= SEQUENCE {
    cucsSwUlanInstanceId                                             CucsManagedObjectId,
    cucsSwUlanDn                                                     CucsManagedObjectDn,
    cucsSwUlanRn                                                     SnmpAdminString,
    cucsSwUlanEpDn                                                   SnmpAdminString,
    cucsSwUlanId                                                     Gauge32,
    cucsSwUlanIfRole                                                 CucsFabricVnetEpIfRole,
    cucsSwUlanIfType                                                 CucsNetworkVnetEpIfType,
    cucsSwUlanLocale                                                 CucsFabricVnetEpLocale,
    cucsSwUlanName                                                   SnmpAdminString,
    cucsSwUlanPeerDn                                                 SnmpAdminString,
    cucsSwUlanPubNwDn                                                SnmpAdminString,
    cucsSwUlanPubNwId                                                Gauge32,
    cucsSwUlanPubNwName                                              SnmpAdminString,
    cucsSwUlanPurpose                                                CucsSwUlanPurpose,
    cucsSwUlanSharing                                                CucsFabricAVlanSharing,
    cucsSwUlanSwitchId                                               CucsNetworkSwitchId,
    cucsSwUlanTransport                                              CucsFabricAVlanTransport,
    cucsSwUlanType                                                   CucsFabricAVlanType,
    cucsSwUlanVlanType                                               CucsFabricEpVlanVlanType,
    cucsSwUlanOperState                                              CucsFabricVlanOperState
}

cucsSwUlanInstanceId OBJECT-TYPE
    SYNTAX       CucsManagedObjectId
    MAX-ACCESS   not-accessible
    STATUS       current
    DESCRIPTION
        "Instance identifier of the managed object."
    ::= { cucsSwUlanEntry 1 }

cucsSwUlanDn OBJECT-TYPE
    SYNTAX       CucsManagedObjectDn
    MAX-ACCESS   read-only
    STATUS       current
    DESCRIPTION
        "Cisco UCS sw:Ulan:dn managed object property"
    ::= { cucsSwUlanEntry 2 }

cucsSwUlanRn OBJECT-TYPE
    SYNTAX       SnmpAdminString
    MAX-ACCESS   read-only
    STATUS       current
    DESCRIPTION
        "Cisco UCS sw:Ulan:rn managed object property"
    ::= { cucsSwUlanEntry 3 }

cucsSwUlanEpDn OBJECT-TYPE
    SYNTAX       SnmpAdminString
    MAX-ACCESS   read-only
    STATUS       current
    DESCRIPTION
        "Cisco UCS sw:Ulan:epDn managed object property"
    ::= { cucsSwUlanEntry 4 }

cucsSwUlanId OBJECT-TYPE
    SYNTAX       Gauge32
    MAX-ACCESS   read-only
    STATUS       current
    DESCRIPTION
        "Cisco UCS sw:Ulan:id managed object property"
    ::= { cucsSwUlanEntry 5 }

cucsSwUlanIfRole OBJECT-TYPE
    SYNTAX       CucsFabricVnetEpIfRole
    MAX-ACCESS   read-only
    STATUS       current
    DESCRIPTION
        "Cisco UCS sw:Ulan:ifRole managed object property"
    ::= { cucsSwUlanEntry 6 }

cucsSwUlanIfType OBJECT-TYPE
    SYNTAX       CucsNetworkVnetEpIfType
    MAX-ACCESS   read-only
    STATUS       current
    DESCRIPTION
        "Cisco UCS sw:Ulan:ifType managed object property"
    ::= { cucsSwUlanEntry 7 }

cucsSwUlanLocale OBJECT-TYPE
    SYNTAX       CucsFabricVnetEpLocale
    MAX-ACCESS   read-only
    STATUS       current
    DESCRIPTION
        "Cisco UCS sw:Ulan:locale managed object property"
    ::= { cucsSwUlanEntry 8 }

cucsSwUlanName OBJECT-TYPE
    SYNTAX       SnmpAdminString
    MAX-ACCESS   read-only
    STATUS       current
    DESCRIPTION
        "Cisco UCS sw:Ulan:name managed object property"
    ::= { cucsSwUlanEntry 9 }

cucsSwUlanPeerDn OBJECT-TYPE
    SYNTAX       SnmpAdminString
    MAX-ACCESS   read-only
    STATUS       current
    DESCRIPTION
        "Cisco UCS sw:Ulan:peerDn managed object property"
    ::= { cucsSwUlanEntry 10 }

cucsSwUlanPubNwDn OBJECT-TYPE
    SYNTAX       SnmpAdminString
    MAX-ACCESS   read-only
    STATUS       current
    DESCRIPTION
        "Cisco UCS sw:Ulan:pubNwDn managed object property"
    ::= { cucsSwUlanEntry 11 }

cucsSwUlanPubNwId OBJECT-TYPE
    SYNTAX       Gauge32
    MAX-ACCESS   read-only
    STATUS       current
    DESCRIPTION
        "Cisco UCS sw:Ulan:pubNwId managed object property"
    ::= { cucsSwUlanEntry 12 }

cucsSwUlanPubNwName OBJECT-TYPE
    SYNTAX       SnmpAdminString
    MAX-ACCESS   read-only
    STATUS       current
    DESCRIPTION
        "Cisco UCS sw:Ulan:pubNwName managed object property"
    ::= { cucsSwUlanEntry 13 }

cucsSwUlanPurpose OBJECT-TYPE
    SYNTAX       CucsSwUlanPurpose
    MAX-ACCESS   read-only
    STATUS       current
    DESCRIPTION
        "Cisco UCS sw:Ulan:purpose managed object property"
    ::= { cucsSwUlanEntry 14 }

cucsSwUlanSharing OBJECT-TYPE
    SYNTAX       CucsFabricAVlanSharing
    MAX-ACCESS   read-only
    STATUS       current
    DESCRIPTION
        "Cisco UCS sw:Ulan:sharing managed object property"
    ::= { cucsSwUlanEntry 15 }

cucsSwUlanSwitchId OBJECT-TYPE
    SYNTAX       CucsNetworkSwitchId
    MAX-ACCESS   read-only
    STATUS       current
    DESCRIPTION
        "Cisco UCS sw:Ulan:switchId managed object property"
    ::= { cucsSwUlanEntry 16 }

cucsSwUlanTransport OBJECT-TYPE
    SYNTAX       CucsFabricAVlanTransport
    MAX-ACCESS   read-only
    STATUS       current
    DESCRIPTION
        "Cisco UCS sw:Ulan:transport managed object property"
    ::= { cucsSwUlanEntry 17 }

cucsSwUlanType OBJECT-TYPE
    SYNTAX       CucsFabricAVlanType
    MAX-ACCESS   read-only
    STATUS       current
    DESCRIPTION
        "Cisco UCS sw:Ulan:type managed object property"
    ::= { cucsSwUlanEntry 18 }

cucsSwUlanVlanType OBJECT-TYPE
    SYNTAX       CucsFabricEpVlanVlanType
    MAX-ACCESS   read-only
    STATUS       current
    DESCRIPTION
        "Cisco UCS sw:Ulan:vlanType managed object property"
    ::= { cucsSwUlanEntry 19 }

cucsSwUlanOperState OBJECT-TYPE
    SYNTAX       CucsFabricVlanOperState
    MAX-ACCESS   read-only
    STATUS       current
    DESCRIPTION
        "Cisco UCS sw:Ulan:operState managed object property"
    ::= { cucsSwUlanEntry 20 }

cucsSwUtilityDomainTable OBJECT-TYPE
    SYNTAX           SEQUENCE OF CucsSwUtilityDomainEntry
    MAX-ACCESS       not-accessible
    STATUS           current
    DESCRIPTION
        "Cisco UCS sw:UtilityDomain managed object table"
    ::= { cucsSwObjects 31 }

cucsSwUtilityDomainEntry OBJECT-TYPE
    SYNTAX           CucsSwUtilityDomainEntry
    MAX-ACCESS       not-accessible
    STATUS           current
    DESCRIPTION
        "Entry for the cucsSwUtilityDomainTable table."
    INDEX { cucsSwUtilityDomainInstanceId }
    ::= { cucsSwUtilityDomainTable 1 }

CucsSwUtilityDomainEntry ::= SEQUENCE {
    cucsSwUtilityDomainInstanceId                                    CucsManagedObjectId,
    cucsSwUtilityDomainDn                                            CucsManagedObjectDn,
    cucsSwUtilityDomainRn                                            SnmpAdminString,
    cucsSwUtilityDomainFsmDescr                                      SnmpAdminString,
    cucsSwUtilityDomainFsmPrev                                       SnmpAdminString,
    cucsSwUtilityDomainFsmProgr                                      Gauge32,
    cucsSwUtilityDomainFsmRmtInvErrCode                              Gauge32,
    cucsSwUtilityDomainFsmRmtInvErrDescr                             SnmpAdminString,
    cucsSwUtilityDomainFsmRmtInvRslt                                 CucsConditionRemoteInvRslt,
    cucsSwUtilityDomainFsmStageDescr                                 SnmpAdminString,
    cucsSwUtilityDomainFsmStamp                                      DateAndTime,
    cucsSwUtilityDomainFsmStatus                                     SnmpAdminString,
    cucsSwUtilityDomainFsmTry                                        Gauge32,
    cucsSwUtilityDomainLocale                                        CucsSwUtilityDomainLocale,
    cucsSwUtilityDomainName                                          SnmpAdminString,
    cucsSwUtilityDomainSwitchId                                      CucsNetworkSwitchId,
    cucsSwUtilityDomainTransport                                     CucsNetworkTransport,
    cucsSwUtilityDomainType                                          CucsSwUtilityDomainType
}

cucsSwUtilityDomainInstanceId OBJECT-TYPE
    SYNTAX       CucsManagedObjectId
    MAX-ACCESS   not-accessible
    STATUS       current
    DESCRIPTION
        "Instance identifier of the managed object."
    ::= { cucsSwUtilityDomainEntry 1 }

cucsSwUtilityDomainDn OBJECT-TYPE
    SYNTAX       CucsManagedObjectDn
    MAX-ACCESS   read-only
    STATUS       current
    DESCRIPTION
        "Cisco UCS sw:UtilityDomain:dn managed object property"
    ::= { cucsSwUtilityDomainEntry 2 }

cucsSwUtilityDomainRn OBJECT-TYPE
    SYNTAX       SnmpAdminString
    MAX-ACCESS   read-only
    STATUS       current
    DESCRIPTION
        "Cisco UCS sw:UtilityDomain:rn managed object property"
    ::= { cucsSwUtilityDomainEntry 3 }

cucsSwUtilityDomainFsmDescr OBJECT-TYPE
    SYNTAX       SnmpAdminString
    MAX-ACCESS   read-only
    STATUS       current
    DESCRIPTION
        "Cisco UCS sw:UtilityDomain:fsmDescr managed object property"
    ::= { cucsSwUtilityDomainEntry 4 }

cucsSwUtilityDomainFsmPrev OBJECT-TYPE
    SYNTAX       SnmpAdminString
    MAX-ACCESS   read-only
    STATUS       current
    DESCRIPTION
        "Cisco UCS sw:UtilityDomain:fsmPrev managed object property"
    ::= { cucsSwUtilityDomainEntry 5 }

cucsSwUtilityDomainFsmProgr OBJECT-TYPE
    SYNTAX       Gauge32
    MAX-ACCESS   read-only
    STATUS       current
    DESCRIPTION
        "Cisco UCS sw:UtilityDomain:fsmProgr managed object property"
    ::= { cucsSwUtilityDomainEntry 6 }

cucsSwUtilityDomainFsmRmtInvErrCode OBJECT-TYPE
    SYNTAX       Gauge32
    MAX-ACCESS   read-only
    STATUS       current
    DESCRIPTION
        "Cisco UCS sw:UtilityDomain:fsmRmtInvErrCode managed
        object property"
    ::= { cucsSwUtilityDomainEntry 7 }

cucsSwUtilityDomainFsmRmtInvErrDescr OBJECT-TYPE
    SYNTAX       SnmpAdminString
    MAX-ACCESS   read-only
    STATUS       current
    DESCRIPTION
        "Cisco UCS sw:UtilityDomain:fsmRmtInvErrDescr managed
        object property"
    ::= { cucsSwUtilityDomainEntry 8 }

cucsSwUtilityDomainFsmRmtInvRslt OBJECT-TYPE
    SYNTAX       CucsConditionRemoteInvRslt
    MAX-ACCESS   read-only
    STATUS       current
    DESCRIPTION
        "Cisco UCS sw:UtilityDomain:fsmRmtInvRslt managed object property"
    ::= { cucsSwUtilityDomainEntry 9 }

cucsSwUtilityDomainFsmStageDescr OBJECT-TYPE
    SYNTAX       SnmpAdminString
    MAX-ACCESS   read-only
    STATUS       current
    DESCRIPTION
        "Cisco UCS sw:UtilityDomain:fsmStageDescr managed object property"
    ::= { cucsSwUtilityDomainEntry 10 }

cucsSwUtilityDomainFsmStamp OBJECT-TYPE
    SYNTAX       DateAndTime
    MAX-ACCESS   read-only
    STATUS       current
    DESCRIPTION
        "Cisco UCS sw:UtilityDomain:fsmStamp managed object property"
    ::= { cucsSwUtilityDomainEntry 11 }

cucsSwUtilityDomainFsmStatus OBJECT-TYPE
    SYNTAX       SnmpAdminString
    MAX-ACCESS   read-only
    STATUS       current
    DESCRIPTION
        "Cisco UCS sw:UtilityDomain:fsmStatus managed object property"
    ::= { cucsSwUtilityDomainEntry 12 }

cucsSwUtilityDomainFsmTry OBJECT-TYPE
    SYNTAX       Gauge32
    MAX-ACCESS   read-only
    STATUS       current
    DESCRIPTION
        "Cisco UCS sw:UtilityDomain:fsmTry managed object property"
    ::= { cucsSwUtilityDomainEntry 13 }

cucsSwUtilityDomainLocale OBJECT-TYPE
    SYNTAX       CucsSwUtilityDomainLocale
    MAX-ACCESS   read-only
    STATUS       current
    DESCRIPTION
        "Cisco UCS sw:UtilityDomain:locale managed object property"
    ::= { cucsSwUtilityDomainEntry 14 }

cucsSwUtilityDomainName OBJECT-TYPE
    SYNTAX       SnmpAdminString
    MAX-ACCESS   read-only
    STATUS       current
    DESCRIPTION
        "Cisco UCS sw:UtilityDomain:name managed object property"
    ::= { cucsSwUtilityDomainEntry 15 }

cucsSwUtilityDomainSwitchId OBJECT-TYPE
    SYNTAX       CucsNetworkSwitchId
    MAX-ACCESS   read-only
    STATUS       current
    DESCRIPTION
        "Cisco UCS sw:UtilityDomain:switchId managed object property"
    ::= { cucsSwUtilityDomainEntry 16 }

cucsSwUtilityDomainTransport OBJECT-TYPE
    SYNTAX       CucsNetworkTransport
    MAX-ACCESS   read-only
    STATUS       current
    DESCRIPTION
        "Cisco UCS sw:UtilityDomain:transport managed object property"
    ::= { cucsSwUtilityDomainEntry 17 }

cucsSwUtilityDomainType OBJECT-TYPE
    SYNTAX       CucsSwUtilityDomainType
    MAX-ACCESS   read-only
    STATUS       current
    DESCRIPTION
        "Cisco UCS sw:UtilityDomain:type managed object property"
    ::= { cucsSwUtilityDomainEntry 18 }

cucsSwUtilityDomainFsmTaskTable OBJECT-TYPE
    SYNTAX           SEQUENCE OF CucsSwUtilityDomainFsmTaskEntry
    MAX-ACCESS       not-accessible
    STATUS           current
    DESCRIPTION
        "Cisco UCS sw:UtilityDomainFsmTask managed object table"
    ::= { cucsSwObjects 32 }

cucsSwUtilityDomainFsmTaskEntry OBJECT-TYPE
    SYNTAX           CucsSwUtilityDomainFsmTaskEntry
    MAX-ACCESS       not-accessible
    STATUS           current
    DESCRIPTION
        "Entry for the cucsSwUtilityDomainFsmTaskTable table."
    INDEX { cucsSwUtilityDomainFsmTaskInstanceId }
    ::= { cucsSwUtilityDomainFsmTaskTable 1 }

CucsSwUtilityDomainFsmTaskEntry ::= SEQUENCE {
    cucsSwUtilityDomainFsmTaskInstanceId                             CucsManagedObjectId,
    cucsSwUtilityDomainFsmTaskDn                                     CucsManagedObjectDn,
    cucsSwUtilityDomainFsmTaskRn                                     SnmpAdminString,
    cucsSwUtilityDomainFsmTaskCompletion                             CucsFsmCompletion,
    cucsSwUtilityDomainFsmTaskFlags                                  CucsFsmFlags,
    cucsSwUtilityDomainFsmTaskItem                                   CucsSwUtilityDomainFsmTaskItem,
    cucsSwUtilityDomainFsmTaskSeqId                                  Gauge32
}

cucsSwUtilityDomainFsmTaskInstanceId OBJECT-TYPE
    SYNTAX       CucsManagedObjectId
    MAX-ACCESS   not-accessible
    STATUS       current
    DESCRIPTION
        "Instance identifier of the managed object."
    ::= { cucsSwUtilityDomainFsmTaskEntry 1 }

cucsSwUtilityDomainFsmTaskDn OBJECT-TYPE
    SYNTAX       CucsManagedObjectDn
    MAX-ACCESS   read-only
    STATUS       current
    DESCRIPTION
        "Cisco UCS sw:UtilityDomainFsmTask:dn managed object property"
    ::= { cucsSwUtilityDomainFsmTaskEntry 2 }

cucsSwUtilityDomainFsmTaskRn OBJECT-TYPE
    SYNTAX       SnmpAdminString
    MAX-ACCESS   read-only
    STATUS       current
    DESCRIPTION
        "Cisco UCS sw:UtilityDomainFsmTask:rn managed object property"
    ::= { cucsSwUtilityDomainFsmTaskEntry 3 }

cucsSwUtilityDomainFsmTaskCompletion OBJECT-TYPE
    SYNTAX       CucsFsmCompletion
    MAX-ACCESS   read-only
    STATUS       current
    DESCRIPTION
        "Cisco UCS sw:UtilityDomainFsmTask:completion managed
        object property"
    ::= { cucsSwUtilityDomainFsmTaskEntry 4 }

cucsSwUtilityDomainFsmTaskFlags OBJECT-TYPE
    SYNTAX       CucsFsmFlags
    MAX-ACCESS   read-only
    STATUS       current
    DESCRIPTION
        "Cisco UCS sw:UtilityDomainFsmTask:flags managed object property"
    ::= { cucsSwUtilityDomainFsmTaskEntry 5 }

cucsSwUtilityDomainFsmTaskItem OBJECT-TYPE
    SYNTAX       CucsSwUtilityDomainFsmTaskItem
    MAX-ACCESS   read-only
    STATUS       current
    DESCRIPTION
        "Cisco UCS sw:UtilityDomainFsmTask:item managed object property"
    ::= { cucsSwUtilityDomainFsmTaskEntry 6 }

cucsSwUtilityDomainFsmTaskSeqId OBJECT-TYPE
    SYNTAX       Gauge32
    MAX-ACCESS   read-only
    STATUS       current
    DESCRIPTION
        "Cisco UCS sw:UtilityDomainFsmTask:seqId managed object property"
    ::= { cucsSwUtilityDomainFsmTaskEntry 7 }

cucsSwVlanTable OBJECT-TYPE
    SYNTAX           SEQUENCE OF CucsSwVlanEntry
    MAX-ACCESS       not-accessible
    STATUS           current
    DESCRIPTION
        "Cisco UCS sw:Vlan managed object table"
    ::= { cucsSwObjects 33 }

cucsSwVlanEntry OBJECT-TYPE
    SYNTAX           CucsSwVlanEntry
    MAX-ACCESS       not-accessible
    STATUS           current
    DESCRIPTION
        "Entry for the cucsSwVlanTable table."
    INDEX { cucsSwVlanInstanceId }
    ::= { cucsSwVlanTable 1 }

CucsSwVlanEntry ::= SEQUENCE {
    cucsSwVlanInstanceId                                             CucsManagedObjectId,
    cucsSwVlanDn                                                     CucsManagedObjectDn,
    cucsSwVlanRn                                                     SnmpAdminString,
    cucsSwVlanEpDn                                                   SnmpAdminString,
    cucsSwVlanId                                                     Gauge32,
    cucsSwVlanIfRole                                                 CucsFabricVnetEpIfRole,
    cucsSwVlanIfType                                                 CucsNetworkVnetEpIfType,
    cucsSwVlanLc                                                     CucsSwVlanLc,
    cucsSwVlanLocale                                                 CucsFabricVnetEpLocale,
    cucsSwVlanMonTrafDir                                             CucsFabricTrafficDirection,
    cucsSwVlanName                                                   SnmpAdminString,
    cucsSwVlanPeerDn                                                 SnmpAdminString,
    cucsSwVlanPubNwDn                                                SnmpAdminString,
    cucsSwVlanPubNwId                                                Gauge32,
    cucsSwVlanPubNwName                                              SnmpAdminString,
    cucsSwVlanSharing                                                CucsFabricAVlanSharing,
    cucsSwVlanSwitchId                                               CucsNetworkSwitchId,
    cucsSwVlanTransport                                              CucsFabricAVlanTransport,
    cucsSwVlanType                                                   CucsFabricAVlanType,
    cucsSwVlanVlanType                                               CucsFabricEpVlanVlanType,
    cucsSwVlanOperState                                              CucsFabricVlanOperState
}

cucsSwVlanInstanceId OBJECT-TYPE
    SYNTAX       CucsManagedObjectId
    MAX-ACCESS   not-accessible
    STATUS       current
    DESCRIPTION
        "Instance identifier of the managed object."
    ::= { cucsSwVlanEntry 1 }

cucsSwVlanDn OBJECT-TYPE
    SYNTAX       CucsManagedObjectDn
    MAX-ACCESS   read-only
    STATUS       current
    DESCRIPTION
        "Cisco UCS sw:Vlan:dn managed object property"
    ::= { cucsSwVlanEntry 2 }

cucsSwVlanRn OBJECT-TYPE
    SYNTAX       SnmpAdminString
    MAX-ACCESS   read-only
    STATUS       current
    DESCRIPTION
        "Cisco UCS sw:Vlan:rn managed object property"
    ::= { cucsSwVlanEntry 3 }

cucsSwVlanEpDn OBJECT-TYPE
    SYNTAX       SnmpAdminString
    MAX-ACCESS   read-only
    STATUS       current
    DESCRIPTION
        "Cisco UCS sw:Vlan:epDn managed object property"
    ::= { cucsSwVlanEntry 4 }

cucsSwVlanId OBJECT-TYPE
    SYNTAX       Gauge32
    MAX-ACCESS   read-only
    STATUS       current
    DESCRIPTION
        "Cisco UCS sw:Vlan:id managed object property"
    ::= { cucsSwVlanEntry 5 }

cucsSwVlanIfRole OBJECT-TYPE
    SYNTAX       CucsFabricVnetEpIfRole
    MAX-ACCESS   read-only
    STATUS       current
    DESCRIPTION
        "Cisco UCS sw:Vlan:ifRole managed object property"
    ::= { cucsSwVlanEntry 6 }

cucsSwVlanIfType OBJECT-TYPE
    SYNTAX       CucsNetworkVnetEpIfType
    MAX-ACCESS   read-only
    STATUS       current
    DESCRIPTION
        "Cisco UCS sw:Vlan:ifType managed object property"
    ::= { cucsSwVlanEntry 7 }

cucsSwVlanLc OBJECT-TYPE
    SYNTAX       CucsSwVlanLc
    MAX-ACCESS   read-only
    STATUS       current
    DESCRIPTION
        "Cisco UCS sw:Vlan:lc managed object property"
    ::= { cucsSwVlanEntry 8 }

cucsSwVlanLocale OBJECT-TYPE
    SYNTAX       CucsFabricVnetEpLocale
    MAX-ACCESS   read-only
    STATUS       current
    DESCRIPTION
        "Cisco UCS sw:Vlan:locale managed object property"
    ::= { cucsSwVlanEntry 9 }

cucsSwVlanMonTrafDir OBJECT-TYPE
    SYNTAX       CucsFabricTrafficDirection
    MAX-ACCESS   read-only
    STATUS       current
    DESCRIPTION
        "Cisco UCS sw:Vlan:monTrafDir managed object property"
    ::= { cucsSwVlanEntry 10 }

cucsSwVlanName OBJECT-TYPE
    SYNTAX       SnmpAdminString
    MAX-ACCESS   read-only
    STATUS       current
    DESCRIPTION
        "Cisco UCS sw:Vlan:name managed object property"
    ::= { cucsSwVlanEntry 11 }

cucsSwVlanPeerDn OBJECT-TYPE
    SYNTAX       SnmpAdminString
    MAX-ACCESS   read-only
    STATUS       current
    DESCRIPTION
        "Cisco UCS sw:Vlan:peerDn managed object property"
    ::= { cucsSwVlanEntry 12 }

cucsSwVlanPubNwDn OBJECT-TYPE
    SYNTAX       SnmpAdminString
    MAX-ACCESS   read-only
    STATUS       current
    DESCRIPTION
        "Cisco UCS sw:Vlan:pubNwDn managed object property"
    ::= { cucsSwVlanEntry 13 }

cucsSwVlanPubNwId OBJECT-TYPE
    SYNTAX       Gauge32
    MAX-ACCESS   read-only
    STATUS       current
    DESCRIPTION
        "Cisco UCS sw:Vlan:pubNwId managed object property"
    ::= { cucsSwVlanEntry 14 }

cucsSwVlanPubNwName OBJECT-TYPE
    SYNTAX       SnmpAdminString
    MAX-ACCESS   read-only
    STATUS       current
    DESCRIPTION
        "Cisco UCS sw:Vlan:pubNwName managed object property"
    ::= { cucsSwVlanEntry 15 }

cucsSwVlanSharing OBJECT-TYPE
    SYNTAX       CucsFabricAVlanSharing
    MAX-ACCESS   read-only
    STATUS       current
    DESCRIPTION
        "Cisco UCS sw:Vlan:sharing managed object property"
    ::= { cucsSwVlanEntry 16 }

cucsSwVlanSwitchId OBJECT-TYPE
    SYNTAX       CucsNetworkSwitchId
    MAX-ACCESS   read-only
    STATUS       current
    DESCRIPTION
        "Cisco UCS sw:Vlan:switchId managed object property"
    ::= { cucsSwVlanEntry 17 }

cucsSwVlanTransport OBJECT-TYPE
    SYNTAX       CucsFabricAVlanTransport
    MAX-ACCESS   read-only
    STATUS       current
    DESCRIPTION
        "Cisco UCS sw:Vlan:transport managed object property"
    ::= { cucsSwVlanEntry 18 }

cucsSwVlanType OBJECT-TYPE
    SYNTAX       CucsFabricAVlanType
    MAX-ACCESS   read-only
    STATUS       current
    DESCRIPTION
        "Cisco UCS sw:Vlan:type managed object property"
    ::= { cucsSwVlanEntry 19 }

cucsSwVlanVlanType OBJECT-TYPE
    SYNTAX       CucsFabricEpVlanVlanType
    MAX-ACCESS   read-only
    STATUS       current
    DESCRIPTION
        "Cisco UCS sw:Vlan:vlanType managed object property"
    ::= { cucsSwVlanEntry 20 }

cucsSwVlanOperState OBJECT-TYPE
    SYNTAX       CucsFabricVlanOperState
    MAX-ACCESS   read-only
    STATUS       current
    DESCRIPTION
        "Cisco UCS sw:Vlan:operState managed object property"
    ::= { cucsSwVlanEntry 21 }

cucsSwVlanPortNsTable OBJECT-TYPE
    SYNTAX           SEQUENCE OF CucsSwVlanPortNsEntry
    MAX-ACCESS       not-accessible
    STATUS           current
    DESCRIPTION
        "Cisco UCS sw:VlanPortNs managed object table"
    ::= { cucsSwObjects 34 }

cucsSwVlanPortNsEntry OBJECT-TYPE
    SYNTAX           CucsSwVlanPortNsEntry
    MAX-ACCESS       not-accessible
    STATUS           current
    DESCRIPTION
        "Entry for the cucsSwVlanPortNsTable table."
    INDEX { cucsSwVlanPortNsInstanceId }
    ::= { cucsSwVlanPortNsTable 1 }

CucsSwVlanPortNsEntry ::= SEQUENCE {
    cucsSwVlanPortNsInstanceId                                       CucsManagedObjectId,
    cucsSwVlanPortNsDn                                               CucsManagedObjectDn,
    cucsSwVlanPortNsRn                                               SnmpAdminString,
    cucsSwVlanPortNsAccessVlanPortCount                              Gauge32,
    cucsSwVlanPortNsAllocStatus                                      CucsSwVlanPortNsAllocStatus,
    cucsSwVlanPortNsBorderVlanPortCount                              Gauge32,
    cucsSwVlanPortNsLimit                                            Gauge32,
    cucsSwVlanPortNsSwitchId                                         CucsNetworkSwitchId
}

cucsSwVlanPortNsInstanceId OBJECT-TYPE
    SYNTAX       CucsManagedObjectId
    MAX-ACCESS   not-accessible
    STATUS       current
    DESCRIPTION
        "Instance identifier of the managed object."
    ::= { cucsSwVlanPortNsEntry 1 }

cucsSwVlanPortNsDn OBJECT-TYPE
    SYNTAX       CucsManagedObjectDn
    MAX-ACCESS   read-only
    STATUS       current
    DESCRIPTION
        "Cisco UCS sw:VlanPortNs:dn managed object property"
    ::= { cucsSwVlanPortNsEntry 2 }

cucsSwVlanPortNsRn OBJECT-TYPE
    SYNTAX       SnmpAdminString
    MAX-ACCESS   read-only
    STATUS       current
    DESCRIPTION
        "Cisco UCS sw:VlanPortNs:rn managed object property"
    ::= { cucsSwVlanPortNsEntry 3 }

cucsSwVlanPortNsAccessVlanPortCount OBJECT-TYPE
    SYNTAX       Gauge32
    MAX-ACCESS   read-only
    STATUS       current
    DESCRIPTION
        "Cisco UCS sw:VlanPortNs:accessVlanPortCount managed
        object property"
    ::= { cucsSwVlanPortNsEntry 4 }

cucsSwVlanPortNsAllocStatus OBJECT-TYPE
    SYNTAX       CucsSwVlanPortNsAllocStatus
    MAX-ACCESS   read-only
    STATUS       current
    DESCRIPTION
        "Cisco UCS sw:VlanPortNs:allocStatus managed object property"
    ::= { cucsSwVlanPortNsEntry 5 }

cucsSwVlanPortNsBorderVlanPortCount OBJECT-TYPE
    SYNTAX       Gauge32
    MAX-ACCESS   read-only
    STATUS       current
    DESCRIPTION
        "Cisco UCS sw:VlanPortNs:borderVlanPortCount managed
        object property"
    ::= { cucsSwVlanPortNsEntry 6 }

cucsSwVlanPortNsLimit OBJECT-TYPE
    SYNTAX       Gauge32
    MAX-ACCESS   read-only
    STATUS       current
    DESCRIPTION
        "Cisco UCS sw:VlanPortNs:limit managed object property"
    ::= { cucsSwVlanPortNsEntry 7 }

cucsSwVlanPortNsSwitchId OBJECT-TYPE
    SYNTAX       CucsNetworkSwitchId
    MAX-ACCESS   read-only
    STATUS       current
    DESCRIPTION
        "Cisco UCS sw:VlanPortNs:switchId managed object property"
    ::= { cucsSwVlanPortNsEntry 8 }

cucsSwVlanPortNsOverrideTable OBJECT-TYPE
    SYNTAX           SEQUENCE OF CucsSwVlanPortNsOverrideEntry
    MAX-ACCESS       not-accessible
    STATUS           current
    DESCRIPTION
        "Cisco UCS sw:VlanPortNsOverride managed object table"
    ::= { cucsSwObjects 37 }

cucsSwVlanPortNsOverrideEntry OBJECT-TYPE
    SYNTAX           CucsSwVlanPortNsOverrideEntry
    MAX-ACCESS       not-accessible
    STATUS           current
    DESCRIPTION
        "Entry for the cucsSwVlanPortNsOverrideTable table."
    INDEX { cucsSwVlanPortNsOverrideInstanceId }
    ::= { cucsSwVlanPortNsOverrideTable 1 }

CucsSwVlanPortNsOverrideEntry ::= SEQUENCE {
    cucsSwVlanPortNsOverrideInstanceId                               CucsManagedObjectId,
    cucsSwVlanPortNsOverrideDn                                       CucsManagedObjectDn,
    cucsSwVlanPortNsOverrideRn                                       SnmpAdminString,
    cucsSwVlanPortNsOverrideLimit                                    Gauge32
}

cucsSwVlanPortNsOverrideInstanceId OBJECT-TYPE
    SYNTAX       CucsManagedObjectId
    MAX-ACCESS   not-accessible
    STATUS       current
    DESCRIPTION
        "Instance identifier of the managed object."
    ::= { cucsSwVlanPortNsOverrideEntry 1 }

cucsSwVlanPortNsOverrideDn OBJECT-TYPE
    SYNTAX       CucsManagedObjectDn
    MAX-ACCESS   read-only
    STATUS       current
    DESCRIPTION
        "Cisco UCS sw:VlanPortNsOverride:dn managed object property"
    ::= { cucsSwVlanPortNsOverrideEntry 2 }

cucsSwVlanPortNsOverrideRn OBJECT-TYPE
    SYNTAX       SnmpAdminString
    MAX-ACCESS   read-only
    STATUS       current
    DESCRIPTION
        "Cisco UCS sw:VlanPortNsOverride:rn managed object property"
    ::= { cucsSwVlanPortNsOverrideEntry 3 }

cucsSwVlanPortNsOverrideLimit OBJECT-TYPE
    SYNTAX       Gauge32
    MAX-ACCESS   read-only
    STATUS       current
    DESCRIPTION
        "Cisco UCS sw:VlanPortNsOverride:limit managed object property"
    ::= { cucsSwVlanPortNsOverrideEntry 4 }

cucsSwVsanTable OBJECT-TYPE
    SYNTAX           SEQUENCE OF CucsSwVsanEntry
    MAX-ACCESS       not-accessible
    STATUS           current
    DESCRIPTION
        "Cisco UCS sw:Vsan managed object table"
    ::= { cucsSwObjects 35 }

cucsSwVsanEntry OBJECT-TYPE
    SYNTAX           CucsSwVsanEntry
    MAX-ACCESS       not-accessible
    STATUS           current
    DESCRIPTION
        "Entry for the cucsSwVsanTable table."
    INDEX { cucsSwVsanInstanceId }
    ::= { cucsSwVsanTable 1 }

CucsSwVsanEntry ::= SEQUENCE {
    cucsSwVsanInstanceId                                             CucsManagedObjectId,
    cucsSwVsanDn                                                     CucsManagedObjectDn,
    cucsSwVsanRn                                                     SnmpAdminString,
    cucsSwVsanEpDn                                                   SnmpAdminString,
    cucsSwVsanFcoeVlan                                               Gauge32,
    cucsSwVsanId                                                     Gauge32,
    cucsSwVsanIfRole                                                 CucsFabricVnetEpIfRole,
    cucsSwVsanIfType                                                 CucsNetworkVnetEpIfType,
    cucsSwVsanLc                                                     CucsFsmLifecycle,
    cucsSwVsanLocale                                                 CucsFabricVnetEpLocale,
    cucsSwVsanMonTrafDir                                             CucsFabricTrafficDirection,
    cucsSwVsanName                                                   SnmpAdminString,
    cucsSwVsanPeerDn                                                 SnmpAdminString,
    cucsSwVsanSwitchId                                               CucsNetworkSwitchId,
    cucsSwVsanTransport                                              CucsFabricAVsanTransport,
    cucsSwVsanType                                                   CucsFabricAVsanType,
    cucsSwVsanDefaultZoning                                          CucsFabricDefaultZoningState,
    cucsSwVsanOperState                                              CucsFabricVsanOperState
}

cucsSwVsanInstanceId OBJECT-TYPE
    SYNTAX       CucsManagedObjectId
    MAX-ACCESS   not-accessible
    STATUS       current
    DESCRIPTION
        "Instance identifier of the managed object."
    ::= { cucsSwVsanEntry 1 }

cucsSwVsanDn OBJECT-TYPE
    SYNTAX       CucsManagedObjectDn
    MAX-ACCESS   read-only
    STATUS       current
    DESCRIPTION
        "Cisco UCS sw:Vsan:dn managed object property"
    ::= { cucsSwVsanEntry 2 }

cucsSwVsanRn OBJECT-TYPE
    SYNTAX       SnmpAdminString
    MAX-ACCESS   read-only
    STATUS       current
    DESCRIPTION
        "Cisco UCS sw:Vsan:rn managed object property"
    ::= { cucsSwVsanEntry 3 }

cucsSwVsanEpDn OBJECT-TYPE
    SYNTAX       SnmpAdminString
    MAX-ACCESS   read-only
    STATUS       current
    DESCRIPTION
        "Cisco UCS sw:Vsan:epDn managed object property"
    ::= { cucsSwVsanEntry 4 }

cucsSwVsanFcoeVlan OBJECT-TYPE
    SYNTAX       Gauge32
    MAX-ACCESS   read-only
    STATUS       current
    DESCRIPTION
        "Cisco UCS sw:Vsan:fcoeVlan managed object property"
    ::= { cucsSwVsanEntry 5 }

cucsSwVsanId OBJECT-TYPE
    SYNTAX       Gauge32
    MAX-ACCESS   read-only
    STATUS       current
    DESCRIPTION
        "Cisco UCS sw:Vsan:id managed object property"
    ::= { cucsSwVsanEntry 6 }

cucsSwVsanIfRole OBJECT-TYPE
    SYNTAX       CucsFabricVnetEpIfRole
    MAX-ACCESS   read-only
    STATUS       current
    DESCRIPTION
        "Cisco UCS sw:Vsan:ifRole managed object property"
    ::= { cucsSwVsanEntry 7 }

cucsSwVsanIfType OBJECT-TYPE
    SYNTAX       CucsNetworkVnetEpIfType
    MAX-ACCESS   read-only
    STATUS       current
    DESCRIPTION
        "Cisco UCS sw:Vsan:ifType managed object property"
    ::= { cucsSwVsanEntry 8 }

cucsSwVsanLc OBJECT-TYPE
    SYNTAX       CucsFsmLifecycle
    MAX-ACCESS   read-only
    STATUS       current
    DESCRIPTION
        "Cisco UCS sw:Vsan:lc managed object property"
    ::= { cucsSwVsanEntry 9 }

cucsSwVsanLocale OBJECT-TYPE
    SYNTAX       CucsFabricVnetEpLocale
    MAX-ACCESS   read-only
    STATUS       current
    DESCRIPTION
        "Cisco UCS sw:Vsan:locale managed object property"
    ::= { cucsSwVsanEntry 10 }

cucsSwVsanMonTrafDir OBJECT-TYPE
    SYNTAX       CucsFabricTrafficDirection
    MAX-ACCESS   read-only
    STATUS       current
    DESCRIPTION
        "Cisco UCS sw:Vsan:monTrafDir managed object property"
    ::= { cucsSwVsanEntry 11 }

cucsSwVsanName OBJECT-TYPE
    SYNTAX       SnmpAdminString
    MAX-ACCESS   read-only
    STATUS       current
    DESCRIPTION
        "Cisco UCS sw:Vsan:name managed object property"
    ::= { cucsSwVsanEntry 12 }

cucsSwVsanPeerDn OBJECT-TYPE
    SYNTAX       SnmpAdminString
    MAX-ACCESS   read-only
    STATUS       current
    DESCRIPTION
        "Cisco UCS sw:Vsan:peerDn managed object property"
    ::= { cucsSwVsanEntry 13 }

cucsSwVsanSwitchId OBJECT-TYPE
    SYNTAX       CucsNetworkSwitchId
    MAX-ACCESS   read-only
    STATUS       current
    DESCRIPTION
        "Cisco UCS sw:Vsan:switchId managed object property"
    ::= { cucsSwVsanEntry 14 }

cucsSwVsanTransport OBJECT-TYPE
    SYNTAX       CucsFabricAVsanTransport
    MAX-ACCESS   read-only
    STATUS       current
    DESCRIPTION
        "Cisco UCS sw:Vsan:transport managed object property"
    ::= { cucsSwVsanEntry 15 }

cucsSwVsanType OBJECT-TYPE
    SYNTAX       CucsFabricAVsanType
    MAX-ACCESS   read-only
    STATUS       current
    DESCRIPTION
        "Cisco UCS sw:Vsan:type managed object property"
    ::= { cucsSwVsanEntry 16 }

cucsSwVsanDefaultZoning OBJECT-TYPE
    SYNTAX       CucsFabricDefaultZoningState
    MAX-ACCESS   read-only
    STATUS       current
    DESCRIPTION
        "Cisco UCS sw:Vsan:defaultZoning managed object property"
    ::= { cucsSwVsanEntry 17 }

cucsSwVsanOperState OBJECT-TYPE
    SYNTAX       CucsFabricVsanOperState
    MAX-ACCESS   read-only
    STATUS       current
    DESCRIPTION
        "Cisco UCS sw:Vsan:operState managed object property"
    ::= { cucsSwVsanEntry 18 }

END
