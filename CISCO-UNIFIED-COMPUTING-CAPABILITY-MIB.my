-- *********************************************************************
-- CISCO-UNIFIED-COMPUTING-CAPABILITY-MIB.my
-- 
-- MIB representation of the Cisco Unified Computing System
-- CAPABILITY management information model package
-- 
-- Created September 2011 by Charles Bullis
-- 
-- Copyright (c) 2005-2011 Cisco Systems, Inc. All rights reserved.
-- 
-- *********************************************************************

CISCO-UNIFIED-COMPUTING-CAPABILITY-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsCapabilityAdminState,
    CucsCapabilityCatalogueFsmTaskItem,
    CucsCapabilityMgmtExtensionFsmTaskItem,
    CucsCapabilityOperStatus,
    CucsCapabilityUpdaterFsmTaskItem,
    CucsConditionRemoteInvRslt,
    CucsFirmwareTransport,
    CucsFsmCompletion,
    CucsFsmFlags
        FROM CISCO-UNIFIED-COMPUTING-TC-MIB;

cucsCapabilityObjects MODULE-IDENTITY
    LAST-UPDATED    "201109150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        CAPABILITY management information model package"
    ::= { ciscoUnifiedComputingMIBObjects 7 }

cucsCapabilityCatalogueTable OBJECT-TYPE
    SYNTAX           SEQUENCE OF CucsCapabilityCatalogueEntry
    MAX-ACCESS       not-accessible
    STATUS           current
    DESCRIPTION
        "Cisco UCS capability:Catalogue managed object table"
    ::= { cucsCapabilityObjects 1 }

cucsCapabilityCatalogueEntry OBJECT-TYPE
    SYNTAX           CucsCapabilityCatalogueEntry
    MAX-ACCESS       not-accessible
    STATUS           current
    DESCRIPTION
        "Entry for the cucsCapabilityCatalogueTable table."
    INDEX { cucsCapabilityCatalogueInstanceId }
    ::= { cucsCapabilityCatalogueTable 1 }

CucsCapabilityCatalogueEntry ::= SEQUENCE {
    cucsCapabilityCatalogueInstanceId                                CucsManagedObjectId,
    cucsCapabilityCatalogueDn                                        CucsManagedObjectDn,
    cucsCapabilityCatalogueRn                                        SnmpAdminString,
    cucsCapabilityCatalogueFsmDescr                                  SnmpAdminString,
    cucsCapabilityCatalogueFsmPrev                                   SnmpAdminString,
    cucsCapabilityCatalogueFsmProgr                                  Gauge32,
    cucsCapabilityCatalogueFsmRmtInvErrCode                          Gauge32,
    cucsCapabilityCatalogueFsmRmtInvErrDescr                         SnmpAdminString,
    cucsCapabilityCatalogueFsmRmtInvRslt                             CucsConditionRemoteInvRslt,
    cucsCapabilityCatalogueFsmStageDescr                             SnmpAdminString,
    cucsCapabilityCatalogueFsmStamp                                  DateAndTime,
    cucsCapabilityCatalogueFsmStatus                                 SnmpAdminString,
    cucsCapabilityCatalogueFsmTry                                    Gauge32,
    cucsCapabilityCatalogueVersion                                   SnmpAdminString
}

cucsCapabilityCatalogueInstanceId OBJECT-TYPE
    SYNTAX       CucsManagedObjectId
    MAX-ACCESS   not-accessible
    STATUS       current
    DESCRIPTION
        "Instance identifier of the managed object."
    ::= { cucsCapabilityCatalogueEntry 1 }

cucsCapabilityCatalogueDn OBJECT-TYPE
    SYNTAX       CucsManagedObjectDn
    MAX-ACCESS   read-only
    STATUS       current
    DESCRIPTION
        "Cisco UCS capability:Catalogue:dn managed object property"
    ::= { cucsCapabilityCatalogueEntry 2 }

cucsCapabilityCatalogueRn OBJECT-TYPE
    SYNTAX       SnmpAdminString
    MAX-ACCESS   read-only
    STATUS       current
    DESCRIPTION
        "Cisco UCS capability:Catalogue:rn managed object property"
    ::= { cucsCapabilityCatalogueEntry 3 }

cucsCapabilityCatalogueFsmDescr OBJECT-TYPE
    SYNTAX       SnmpAdminString
    MAX-ACCESS   read-only
    STATUS       current
    DESCRIPTION
        "Cisco UCS capability:Catalogue:fsmDescr managed object property"
    ::= { cucsCapabilityCatalogueEntry 4 }

cucsCapabilityCatalogueFsmPrev OBJECT-TYPE
    SYNTAX       SnmpAdminString
    MAX-ACCESS   read-only
    STATUS       current
    DESCRIPTION
        "Cisco UCS capability:Catalogue:fsmPrev managed object property"
    ::= { cucsCapabilityCatalogueEntry 5 }

cucsCapabilityCatalogueFsmProgr OBJECT-TYPE
    SYNTAX       Gauge32
    MAX-ACCESS   read-only
    STATUS       current
    DESCRIPTION
        "Cisco UCS capability:Catalogue:fsmProgr managed object property"
    ::= { cucsCapabilityCatalogueEntry 6 }

cucsCapabilityCatalogueFsmRmtInvErrCode OBJECT-TYPE
    SYNTAX       Gauge32
    MAX-ACCESS   read-only
    STATUS       current
    DESCRIPTION
        "Cisco UCS capability:Catalogue:fsmRmtInvErrCode
        managed object property"
    ::= { cucsCapabilityCatalogueEntry 7 }

cucsCapabilityCatalogueFsmRmtInvErrDescr OBJECT-TYPE
    SYNTAX       SnmpAdminString
    MAX-ACCESS   read-only
    STATUS       current
    DESCRIPTION
        "Cisco UCS capability:Catalogue:fsmRmtInvErrDescr
        managed object property"
    ::= { cucsCapabilityCatalogueEntry 8 }

cucsCapabilityCatalogueFsmRmtInvRslt OBJECT-TYPE
    SYNTAX       CucsConditionRemoteInvRslt
    MAX-ACCESS   read-only
    STATUS       current
    DESCRIPTION
        "Cisco UCS capability:Catalogue:fsmRmtInvRslt managed
        object property"
    ::= { cucsCapabilityCatalogueEntry 9 }

cucsCapabilityCatalogueFsmStageDescr OBJECT-TYPE
    SYNTAX       SnmpAdminString
    MAX-ACCESS   read-only
    STATUS       current
    DESCRIPTION
        "Cisco UCS capability:Catalogue:fsmStageDescr managed
        object property"
    ::= { cucsCapabilityCatalogueEntry 10 }

cucsCapabilityCatalogueFsmStamp OBJECT-TYPE
    SYNTAX       DateAndTime
    MAX-ACCESS   read-only
    STATUS       current
    DESCRIPTION
        "Cisco UCS capability:Catalogue:fsmStamp managed object property"
    ::= { cucsCapabilityCatalogueEntry 11 }

cucsCapabilityCatalogueFsmStatus OBJECT-TYPE
    SYNTAX       SnmpAdminString
    MAX-ACCESS   read-only
    STATUS       current
    DESCRIPTION
        "Cisco UCS capability:Catalogue:fsmStatus managed object property"
    ::= { cucsCapabilityCatalogueEntry 12 }

cucsCapabilityCatalogueFsmTry OBJECT-TYPE
    SYNTAX       Gauge32
    MAX-ACCESS   read-only
    STATUS       current
    DESCRIPTION
        "Cisco UCS capability:Catalogue:fsmTry managed object property"
    ::= { cucsCapabilityCatalogueEntry 13 }

cucsCapabilityCatalogueVersion OBJECT-TYPE
    SYNTAX       SnmpAdminString
    MAX-ACCESS   read-only
    STATUS       current
    DESCRIPTION
        "Cisco UCS capability:Catalogue:version managed object property"
    ::= { cucsCapabilityCatalogueEntry 14 }

cucsCapabilityCatalogueFsmTaskTable OBJECT-TYPE
    SYNTAX           SEQUENCE OF CucsCapabilityCatalogueFsmTaskEntry
    MAX-ACCESS       not-accessible
    STATUS           current
    DESCRIPTION
        "Cisco UCS capability:CatalogueFsmTask managed object table"
    ::= { cucsCapabilityObjects 2 }

cucsCapabilityCatalogueFsmTaskEntry OBJECT-TYPE
    SYNTAX           CucsCapabilityCatalogueFsmTaskEntry
    MAX-ACCESS       not-accessible
    STATUS           current
    DESCRIPTION
        "Entry for the cucsCapabilityCatalogueFsmTaskTable table."
    INDEX { cucsCapabilityCatalogueFsmTaskInstanceId }
    ::= { cucsCapabilityCatalogueFsmTaskTable 1 }

CucsCapabilityCatalogueFsmTaskEntry ::= SEQUENCE {
    cucsCapabilityCatalogueFsmTaskInstanceId                         CucsManagedObjectId,
    cucsCapabilityCatalogueFsmTaskDn                                 CucsManagedObjectDn,
    cucsCapabilityCatalogueFsmTaskRn                                 SnmpAdminString,
    cucsCapabilityCatalogueFsmTaskCompletion                         CucsFsmCompletion,
    cucsCapabilityCatalogueFsmTaskFlags                              CucsFsmFlags,
    cucsCapabilityCatalogueFsmTaskItem                               CucsCapabilityCatalogueFsmTaskItem,
    cucsCapabilityCatalogueFsmTaskSeqId                              Gauge32
}

cucsCapabilityCatalogueFsmTaskInstanceId OBJECT-TYPE
    SYNTAX       CucsManagedObjectId
    MAX-ACCESS   not-accessible
    STATUS       current
    DESCRIPTION
        "Instance identifier of the managed object."
    ::= { cucsCapabilityCatalogueFsmTaskEntry 1 }

cucsCapabilityCatalogueFsmTaskDn OBJECT-TYPE
    SYNTAX       CucsManagedObjectDn
    MAX-ACCESS   read-only
    STATUS       current
    DESCRIPTION
        "Cisco UCS capability:CatalogueFsmTask:dn managed object property"
    ::= { cucsCapabilityCatalogueFsmTaskEntry 2 }

cucsCapabilityCatalogueFsmTaskRn OBJECT-TYPE
    SYNTAX       SnmpAdminString
    MAX-ACCESS   read-only
    STATUS       current
    DESCRIPTION
        "Cisco UCS capability:CatalogueFsmTask:rn managed object property"
    ::= { cucsCapabilityCatalogueFsmTaskEntry 3 }

cucsCapabilityCatalogueFsmTaskCompletion OBJECT-TYPE
    SYNTAX       CucsFsmCompletion
    MAX-ACCESS   read-only
    STATUS       current
    DESCRIPTION
        "Cisco UCS capability:CatalogueFsmTask:completion
        managed object property"
    ::= { cucsCapabilityCatalogueFsmTaskEntry 4 }

cucsCapabilityCatalogueFsmTaskFlags OBJECT-TYPE
    SYNTAX       CucsFsmFlags
    MAX-ACCESS   read-only
    STATUS       current
    DESCRIPTION
        "Cisco UCS capability:CatalogueFsmTask:flags managed
        object property"
    ::= { cucsCapabilityCatalogueFsmTaskEntry 5 }

cucsCapabilityCatalogueFsmTaskItem OBJECT-TYPE
    SYNTAX       CucsCapabilityCatalogueFsmTaskItem
    MAX-ACCESS   read-only
    STATUS       current
    DESCRIPTION
        "Cisco UCS capability:CatalogueFsmTask:item managed
        object property"
    ::= { cucsCapabilityCatalogueFsmTaskEntry 6 }

cucsCapabilityCatalogueFsmTaskSeqId OBJECT-TYPE
    SYNTAX       Gauge32
    MAX-ACCESS   read-only
    STATUS       current
    DESCRIPTION
        "Cisco UCS capability:CatalogueFsmTask:seqId managed
        object property"
    ::= { cucsCapabilityCatalogueFsmTaskEntry 7 }

cucsCapabilityEpTable OBJECT-TYPE
    SYNTAX           SEQUENCE OF CucsCapabilityEpEntry
    MAX-ACCESS       not-accessible
    STATUS           current
    DESCRIPTION
        "Cisco UCS capability:Ep managed object table"
    ::= { cucsCapabilityObjects 3 }

cucsCapabilityEpEntry OBJECT-TYPE
    SYNTAX           CucsCapabilityEpEntry
    MAX-ACCESS       not-accessible
    STATUS           current
    DESCRIPTION
        "Entry for the cucsCapabilityEpTable table."
    INDEX { cucsCapabilityEpInstanceId }
    ::= { cucsCapabilityEpTable 1 }

CucsCapabilityEpEntry ::= SEQUENCE {
    cucsCapabilityEpInstanceId                                       CucsManagedObjectId,
    cucsCapabilityEpDn                                               CucsManagedObjectDn,
    cucsCapabilityEpRn                                               SnmpAdminString
}

cucsCapabilityEpInstanceId OBJECT-TYPE
    SYNTAX       CucsManagedObjectId
    MAX-ACCESS   not-accessible
    STATUS       current
    DESCRIPTION
        "Instance identifier of the managed object."
    ::= { cucsCapabilityEpEntry 1 }

cucsCapabilityEpDn OBJECT-TYPE
    SYNTAX       CucsManagedObjectDn
    MAX-ACCESS   read-only
    STATUS       current
    DESCRIPTION
        "Cisco UCS capability:Ep:dn managed object property"
    ::= { cucsCapabilityEpEntry 2 }

cucsCapabilityEpRn OBJECT-TYPE
    SYNTAX       SnmpAdminString
    MAX-ACCESS   read-only
    STATUS       current
    DESCRIPTION
        "Cisco UCS capability:Ep:rn managed object property"
    ::= { cucsCapabilityEpEntry 3 }

cucsCapabilityMgmtExtensionTable OBJECT-TYPE
    SYNTAX           SEQUENCE OF CucsCapabilityMgmtExtensionEntry
    MAX-ACCESS       not-accessible
    STATUS           current
    DESCRIPTION
        "Cisco UCS capability:MgmtExtension managed object table"
    ::= { cucsCapabilityObjects 4 }

cucsCapabilityMgmtExtensionEntry OBJECT-TYPE
    SYNTAX           CucsCapabilityMgmtExtensionEntry
    MAX-ACCESS       not-accessible
    STATUS           current
    DESCRIPTION
        "Entry for the cucsCapabilityMgmtExtensionTable table."
    INDEX { cucsCapabilityMgmtExtensionInstanceId }
    ::= { cucsCapabilityMgmtExtensionTable 1 }

CucsCapabilityMgmtExtensionEntry ::= SEQUENCE {
    cucsCapabilityMgmtExtensionInstanceId                            CucsManagedObjectId,
    cucsCapabilityMgmtExtensionDn                                    CucsManagedObjectDn,
    cucsCapabilityMgmtExtensionRn                                    SnmpAdminString,
    cucsCapabilityMgmtExtensionFsmDescr                              SnmpAdminString,
    cucsCapabilityMgmtExtensionFsmPrev                               SnmpAdminString,
    cucsCapabilityMgmtExtensionFsmProgr                              Gauge32,
    cucsCapabilityMgmtExtensionFsmRmtInvErrCode                      Gauge32,
    cucsCapabilityMgmtExtensionFsmRmtInvErrDescr                     SnmpAdminString,
    cucsCapabilityMgmtExtensionFsmRmtInvRslt                         CucsConditionRemoteInvRslt,
    cucsCapabilityMgmtExtensionFsmStageDescr                         SnmpAdminString,
    cucsCapabilityMgmtExtensionFsmStamp                              DateAndTime,
    cucsCapabilityMgmtExtensionFsmStatus                             SnmpAdminString,
    cucsCapabilityMgmtExtensionFsmTry                                Gauge32
}

cucsCapabilityMgmtExtensionInstanceId OBJECT-TYPE
    SYNTAX       CucsManagedObjectId
    MAX-ACCESS   not-accessible
    STATUS       current
    DESCRIPTION
        "Instance identifier of the managed object."
    ::= { cucsCapabilityMgmtExtensionEntry 1 }

cucsCapabilityMgmtExtensionDn OBJECT-TYPE
    SYNTAX       CucsManagedObjectDn
    MAX-ACCESS   read-only
    STATUS       current
    DESCRIPTION
        "Cisco UCS capability:MgmtExtension:dn managed object property"
    ::= { cucsCapabilityMgmtExtensionEntry 2 }

cucsCapabilityMgmtExtensionRn OBJECT-TYPE
    SYNTAX       SnmpAdminString
    MAX-ACCESS   read-only
    STATUS       current
    DESCRIPTION
        "Cisco UCS capability:MgmtExtension:rn managed object property"
    ::= { cucsCapabilityMgmtExtensionEntry 3 }

cucsCapabilityMgmtExtensionFsmDescr OBJECT-TYPE
    SYNTAX       SnmpAdminString
    MAX-ACCESS   read-only
    STATUS       current
    DESCRIPTION
        "Cisco UCS capability:MgmtExtension:fsmDescr managed
        object property"
    ::= { cucsCapabilityMgmtExtensionEntry 4 }

cucsCapabilityMgmtExtensionFsmPrev OBJECT-TYPE
    SYNTAX       SnmpAdminString
    MAX-ACCESS   read-only
    STATUS       current
    DESCRIPTION
        "Cisco UCS capability:MgmtExtension:fsmPrev managed
        object property"
    ::= { cucsCapabilityMgmtExtensionEntry 5 }

cucsCapabilityMgmtExtensionFsmProgr OBJECT-TYPE
    SYNTAX       Gauge32
    MAX-ACCESS   read-only
    STATUS       current
    DESCRIPTION
        "Cisco UCS capability:MgmtExtension:fsmProgr managed
        object property"
    ::= { cucsCapabilityMgmtExtensionEntry 6 }

cucsCapabilityMgmtExtensionFsmRmtInvErrCode OBJECT-TYPE
    SYNTAX       Gauge32
    MAX-ACCESS   read-only
    STATUS       current
    DESCRIPTION
        "Cisco UCS capability:MgmtExtension:fsmRmtInvErrCode
        managed object property"
    ::= { cucsCapabilityMgmtExtensionEntry 7 }

cucsCapabilityMgmtExtensionFsmRmtInvErrDescr OBJECT-TYPE
    SYNTAX       SnmpAdminString
    MAX-ACCESS   read-only
    STATUS       current
    DESCRIPTION
        "Cisco UCS capability:MgmtExtension:fsmRmtInvErrDescr
        managed object property"
    ::= { cucsCapabilityMgmtExtensionEntry 8 }

cucsCapabilityMgmtExtensionFsmRmtInvRslt OBJECT-TYPE
    SYNTAX       CucsConditionRemoteInvRslt
    MAX-ACCESS   read-only
    STATUS       current
    DESCRIPTION
        "Cisco UCS capability:MgmtExtension:fsmRmtInvRslt
        managed object property"
    ::= { cucsCapabilityMgmtExtensionEntry 9 }

cucsCapabilityMgmtExtensionFsmStageDescr OBJECT-TYPE
    SYNTAX       SnmpAdminString
    MAX-ACCESS   read-only
    STATUS       current
    DESCRIPTION
        "Cisco UCS capability:MgmtExtension:fsmStageDescr
        managed object property"
    ::= { cucsCapabilityMgmtExtensionEntry 10 }

cucsCapabilityMgmtExtensionFsmStamp OBJECT-TYPE
    SYNTAX       DateAndTime
    MAX-ACCESS   read-only
    STATUS       current
    DESCRIPTION
        "Cisco UCS capability:MgmtExtension:fsmStamp managed
        object property"
    ::= { cucsCapabilityMgmtExtensionEntry 11 }

cucsCapabilityMgmtExtensionFsmStatus OBJECT-TYPE
    SYNTAX       SnmpAdminString
    MAX-ACCESS   read-only
    STATUS       current
    DESCRIPTION
        "Cisco UCS capability:MgmtExtension:fsmStatus managed
        object property"
    ::= { cucsCapabilityMgmtExtensionEntry 12 }

cucsCapabilityMgmtExtensionFsmTry OBJECT-TYPE
    SYNTAX       Gauge32
    MAX-ACCESS   read-only
    STATUS       current
    DESCRIPTION
        "Cisco UCS capability:MgmtExtension:fsmTry managed
        object property"
    ::= { cucsCapabilityMgmtExtensionEntry 13 }

cucsCapabilityMgmtExtensionFsmTaskTable OBJECT-TYPE
    SYNTAX           SEQUENCE OF CucsCapabilityMgmtExtensionFsmTaskEntry
    MAX-ACCESS       not-accessible
    STATUS           current
    DESCRIPTION
        "Cisco UCS capability:MgmtExtensionFsmTask managed object table"
    ::= { cucsCapabilityObjects 5 }

cucsCapabilityMgmtExtensionFsmTaskEntry OBJECT-TYPE
    SYNTAX           CucsCapabilityMgmtExtensionFsmTaskEntry
    MAX-ACCESS       not-accessible
    STATUS           current
    DESCRIPTION
        "Entry for the cucsCapabilityMgmtExtensionFsmTaskTable table."
    INDEX { cucsCapabilityMgmtExtensionFsmTaskInstanceId }
    ::= { cucsCapabilityMgmtExtensionFsmTaskTable 1 }

CucsCapabilityMgmtExtensionFsmTaskEntry ::= SEQUENCE {
    cucsCapabilityMgmtExtensionFsmTaskInstanceId                     CucsManagedObjectId,
    cucsCapabilityMgmtExtensionFsmTaskDn                             CucsManagedObjectDn,
    cucsCapabilityMgmtExtensionFsmTaskRn                             SnmpAdminString,
    cucsCapabilityMgmtExtensionFsmTaskCompletion                     CucsFsmCompletion,
    cucsCapabilityMgmtExtensionFsmTaskFlags                          CucsFsmFlags,
    cucsCapabilityMgmtExtensionFsmTaskItem                           CucsCapabilityMgmtExtensionFsmTaskItem,
    cucsCapabilityMgmtExtensionFsmTaskSeqId                          Gauge32
}

cucsCapabilityMgmtExtensionFsmTaskInstanceId OBJECT-TYPE
    SYNTAX       CucsManagedObjectId
    MAX-ACCESS   not-accessible
    STATUS       current
    DESCRIPTION
        "Instance identifier of the managed object."
    ::= { cucsCapabilityMgmtExtensionFsmTaskEntry 1 }

cucsCapabilityMgmtExtensionFsmTaskDn OBJECT-TYPE
    SYNTAX       CucsManagedObjectDn
    MAX-ACCESS   read-only
    STATUS       current
    DESCRIPTION
        "Cisco UCS capability:MgmtExtensionFsmTask:dn managed
        object property"
    ::= { cucsCapabilityMgmtExtensionFsmTaskEntry 2 }

cucsCapabilityMgmtExtensionFsmTaskRn OBJECT-TYPE
    SYNTAX       SnmpAdminString
    MAX-ACCESS   read-only
    STATUS       current
    DESCRIPTION
        "Cisco UCS capability:MgmtExtensionFsmTask:rn managed
        object property"
    ::= { cucsCapabilityMgmtExtensionFsmTaskEntry 3 }

cucsCapabilityMgmtExtensionFsmTaskCompletion OBJECT-TYPE
    SYNTAX       CucsFsmCompletion
    MAX-ACCESS   read-only
    STATUS       current
    DESCRIPTION
        "Cisco UCS capability:MgmtExtensionFsmTask:completion
        managed object property"
    ::= { cucsCapabilityMgmtExtensionFsmTaskEntry 4 }

cucsCapabilityMgmtExtensionFsmTaskFlags OBJECT-TYPE
    SYNTAX       CucsFsmFlags
    MAX-ACCESS   read-only
    STATUS       current
    DESCRIPTION
        "Cisco UCS capability:MgmtExtensionFsmTask:flags
        managed object property"
    ::= { cucsCapabilityMgmtExtensionFsmTaskEntry 5 }

cucsCapabilityMgmtExtensionFsmTaskItem OBJECT-TYPE
    SYNTAX       CucsCapabilityMgmtExtensionFsmTaskItem
    MAX-ACCESS   read-only
    STATUS       current
    DESCRIPTION
        "Cisco UCS capability:MgmtExtensionFsmTask:item
        managed object property"
    ::= { cucsCapabilityMgmtExtensionFsmTaskEntry 6 }

cucsCapabilityMgmtExtensionFsmTaskSeqId OBJECT-TYPE
    SYNTAX       Gauge32
    MAX-ACCESS   read-only
    STATUS       current
    DESCRIPTION
        "Cisco UCS capability:MgmtExtensionFsmTask:seqId
        managed object property"
    ::= { cucsCapabilityMgmtExtensionFsmTaskEntry 7 }

cucsCapabilityUpdateTable OBJECT-TYPE
    SYNTAX           SEQUENCE OF CucsCapabilityUpdateEntry
    MAX-ACCESS       not-accessible
    STATUS           current
    DESCRIPTION
        "Cisco UCS capability:Update managed object table"
    ::= { cucsCapabilityObjects 6 }

cucsCapabilityUpdateEntry OBJECT-TYPE
    SYNTAX           CucsCapabilityUpdateEntry
    MAX-ACCESS       not-accessible
    STATUS           current
    DESCRIPTION
        "Entry for the cucsCapabilityUpdateTable table."
    INDEX { cucsCapabilityUpdateInstanceId }
    ::= { cucsCapabilityUpdateTable 1 }

CucsCapabilityUpdateEntry ::= SEQUENCE {
    cucsCapabilityUpdateInstanceId                                   CucsManagedObjectId,
    cucsCapabilityUpdateDn                                           CucsManagedObjectDn,
    cucsCapabilityUpdateRn                                           SnmpAdminString,
    cucsCapabilityUpdateImageName                                    SnmpAdminString,
    cucsCapabilityUpdateUpdateTs                                     DateAndTime,
    cucsCapabilityUpdateVersion                                      SnmpAdminString
}

cucsCapabilityUpdateInstanceId OBJECT-TYPE
    SYNTAX       CucsManagedObjectId
    MAX-ACCESS   not-accessible
    STATUS       current
    DESCRIPTION
        "Instance identifier of the managed object."
    ::= { cucsCapabilityUpdateEntry 1 }

cucsCapabilityUpdateDn OBJECT-TYPE
    SYNTAX       CucsManagedObjectDn
    MAX-ACCESS   read-only
    STATUS       current
    DESCRIPTION
        "Cisco UCS capability:Update:dn managed object property"
    ::= { cucsCapabilityUpdateEntry 2 }

cucsCapabilityUpdateRn OBJECT-TYPE
    SYNTAX       SnmpAdminString
    MAX-ACCESS   read-only
    STATUS       current
    DESCRIPTION
        "Cisco UCS capability:Update:rn managed object property"
    ::= { cucsCapabilityUpdateEntry 3 }

cucsCapabilityUpdateImageName OBJECT-TYPE
    SYNTAX       SnmpAdminString
    MAX-ACCESS   read-only
    STATUS       current
    DESCRIPTION
        "Cisco UCS capability:Update:imageName managed object property"
    ::= { cucsCapabilityUpdateEntry 4 }

cucsCapabilityUpdateUpdateTs OBJECT-TYPE
    SYNTAX       DateAndTime
    MAX-ACCESS   read-only
    STATUS       current
    DESCRIPTION
        "Cisco UCS capability:Update:updateTs managed object property"
    ::= { cucsCapabilityUpdateEntry 5 }

cucsCapabilityUpdateVersion OBJECT-TYPE
    SYNTAX       SnmpAdminString
    MAX-ACCESS   read-only
    STATUS       current
    DESCRIPTION
        "Cisco UCS capability:Update:version managed object property"
    ::= { cucsCapabilityUpdateEntry 6 }

cucsCapabilityUpdaterTable OBJECT-TYPE
    SYNTAX           SEQUENCE OF CucsCapabilityUpdaterEntry
    MAX-ACCESS       not-accessible
    STATUS           current
    DESCRIPTION
        "Cisco UCS capability:Updater managed object table"
    ::= { cucsCapabilityObjects 7 }

cucsCapabilityUpdaterEntry OBJECT-TYPE
    SYNTAX           CucsCapabilityUpdaterEntry
    MAX-ACCESS       not-accessible
    STATUS           current
    DESCRIPTION
        "Entry for the cucsCapabilityUpdaterTable table."
    INDEX { cucsCapabilityUpdaterInstanceId }
    ::= { cucsCapabilityUpdaterTable 1 }

CucsCapabilityUpdaterEntry ::= SEQUENCE {
    cucsCapabilityUpdaterInstanceId                                  CucsManagedObjectId,
    cucsCapabilityUpdaterDn                                          CucsManagedObjectDn,
    cucsCapabilityUpdaterRn                                          SnmpAdminString,
    cucsCapabilityUpdaterAdminState                                  CucsCapabilityAdminState,
    cucsCapabilityUpdaterFileName                                    SnmpAdminString,
    cucsCapabilityUpdaterFsmDescr                                    SnmpAdminString,
    cucsCapabilityUpdaterFsmPrev                                     SnmpAdminString,
    cucsCapabilityUpdaterFsmProgr                                    Gauge32,
    cucsCapabilityUpdaterFsmRmtInvErrCode                            Gauge32,
    cucsCapabilityUpdaterFsmRmtInvErrDescr                           SnmpAdminString,
    cucsCapabilityUpdaterFsmRmtInvRslt                               CucsConditionRemoteInvRslt,
    cucsCapabilityUpdaterFsmStageDescr                               SnmpAdminString,
    cucsCapabilityUpdaterFsmStamp                                    DateAndTime,
    cucsCapabilityUpdaterFsmStatus                                   SnmpAdminString,
    cucsCapabilityUpdaterFsmTry                                      Gauge32,
    cucsCapabilityUpdaterImageName                                   SnmpAdminString,
    cucsCapabilityUpdaterOperState                                   CucsCapabilityOperStatus,
    cucsCapabilityUpdaterProtocol                                    CucsFirmwareTransport,
    cucsCapabilityUpdaterPwd                                         SnmpAdminString,
    cucsCapabilityUpdaterRemotePath                                  SnmpAdminString,
    cucsCapabilityUpdaterServer                                      SnmpAdminString,
    cucsCapabilityUpdaterUser                                        SnmpAdminString,
    cucsCapabilityUpdaterVersion                                     SnmpAdminString
}

cucsCapabilityUpdaterInstanceId OBJECT-TYPE
    SYNTAX       CucsManagedObjectId
    MAX-ACCESS   not-accessible
    STATUS       current
    DESCRIPTION
        "Instance identifier of the managed object."
    ::= { cucsCapabilityUpdaterEntry 1 }

cucsCapabilityUpdaterDn OBJECT-TYPE
    SYNTAX       CucsManagedObjectDn
    MAX-ACCESS   read-only
    STATUS       current
    DESCRIPTION
        "Cisco UCS capability:Updater:dn managed object property"
    ::= { cucsCapabilityUpdaterEntry 2 }

cucsCapabilityUpdaterRn OBJECT-TYPE
    SYNTAX       SnmpAdminString
    MAX-ACCESS   read-only
    STATUS       current
    DESCRIPTION
        "Cisco UCS capability:Updater:rn managed object property"
    ::= { cucsCapabilityUpdaterEntry 3 }

cucsCapabilityUpdaterAdminState OBJECT-TYPE
    SYNTAX       CucsCapabilityAdminState
    MAX-ACCESS   read-only
    STATUS       current
    DESCRIPTION
        "Cisco UCS capability:Updater:adminState managed object property"
    ::= { cucsCapabilityUpdaterEntry 4 }

cucsCapabilityUpdaterFileName OBJECT-TYPE
    SYNTAX       SnmpAdminString
    MAX-ACCESS   read-only
    STATUS       current
    DESCRIPTION
        "Cisco UCS capability:Updater:fileName managed object property"
    ::= { cucsCapabilityUpdaterEntry 5 }

cucsCapabilityUpdaterFsmDescr OBJECT-TYPE
    SYNTAX       SnmpAdminString
    MAX-ACCESS   read-only
    STATUS       current
    DESCRIPTION
        "Cisco UCS capability:Updater:fsmDescr managed object property"
    ::= { cucsCapabilityUpdaterEntry 6 }

cucsCapabilityUpdaterFsmPrev OBJECT-TYPE
    SYNTAX       SnmpAdminString
    MAX-ACCESS   read-only
    STATUS       current
    DESCRIPTION
        "Cisco UCS capability:Updater:fsmPrev managed object property"
    ::= { cucsCapabilityUpdaterEntry 7 }

cucsCapabilityUpdaterFsmProgr OBJECT-TYPE
    SYNTAX       Gauge32
    MAX-ACCESS   read-only
    STATUS       current
    DESCRIPTION
        "Cisco UCS capability:Updater:fsmProgr managed object property"
    ::= { cucsCapabilityUpdaterEntry 8 }

cucsCapabilityUpdaterFsmRmtInvErrCode OBJECT-TYPE
    SYNTAX       Gauge32
    MAX-ACCESS   read-only
    STATUS       current
    DESCRIPTION
        "Cisco UCS capability:Updater:fsmRmtInvErrCode
        managed object property"
    ::= { cucsCapabilityUpdaterEntry 9 }

cucsCapabilityUpdaterFsmRmtInvErrDescr OBJECT-TYPE
    SYNTAX       SnmpAdminString
    MAX-ACCESS   read-only
    STATUS       current
    DESCRIPTION
        "Cisco UCS capability:Updater:fsmRmtInvErrDescr
        managed object property"
    ::= { cucsCapabilityUpdaterEntry 10 }

cucsCapabilityUpdaterFsmRmtInvRslt OBJECT-TYPE
    SYNTAX       CucsConditionRemoteInvRslt
    MAX-ACCESS   read-only
    STATUS       current
    DESCRIPTION
        "Cisco UCS capability:Updater:fsmRmtInvRslt managed
        object property"
    ::= { cucsCapabilityUpdaterEntry 11 }

cucsCapabilityUpdaterFsmStageDescr OBJECT-TYPE
    SYNTAX       SnmpAdminString
    MAX-ACCESS   read-only
    STATUS       current
    DESCRIPTION
        "Cisco UCS capability:Updater:fsmStageDescr managed
        object property"
    ::= { cucsCapabilityUpdaterEntry 12 }

cucsCapabilityUpdaterFsmStamp OBJECT-TYPE
    SYNTAX       DateAndTime
    MAX-ACCESS   read-only
    STATUS       current
    DESCRIPTION
        "Cisco UCS capability:Updater:fsmStamp managed object property"
    ::= { cucsCapabilityUpdaterEntry 13 }

cucsCapabilityUpdaterFsmStatus OBJECT-TYPE
    SYNTAX       SnmpAdminString
    MAX-ACCESS   read-only
    STATUS       current
    DESCRIPTION
        "Cisco UCS capability:Updater:fsmStatus managed object property"
    ::= { cucsCapabilityUpdaterEntry 14 }

cucsCapabilityUpdaterFsmTry OBJECT-TYPE
    SYNTAX       Gauge32
    MAX-ACCESS   read-only
    STATUS       current
    DESCRIPTION
        "Cisco UCS capability:Updater:fsmTry managed object property"
    ::= { cucsCapabilityUpdaterEntry 15 }

cucsCapabilityUpdaterImageName OBJECT-TYPE
    SYNTAX       SnmpAdminString
    MAX-ACCESS   read-only
    STATUS       current
    DESCRIPTION
        "Cisco UCS capability:Updater:imageName managed object property"
    ::= { cucsCapabilityUpdaterEntry 16 }

cucsCapabilityUpdaterOperState OBJECT-TYPE
    SYNTAX       CucsCapabilityOperStatus
    MAX-ACCESS   read-only
    STATUS       current
    DESCRIPTION
        "Cisco UCS capability:Updater:operState managed object property"
    ::= { cucsCapabilityUpdaterEntry 17 }

cucsCapabilityUpdaterProtocol OBJECT-TYPE
    SYNTAX       CucsFirmwareTransport
    MAX-ACCESS   read-only
    STATUS       current
    DESCRIPTION
        "Cisco UCS capability:Updater:protocol managed object property"
    ::= { cucsCapabilityUpdaterEntry 18 }

cucsCapabilityUpdaterPwd OBJECT-TYPE
    SYNTAX       SnmpAdminString
    MAX-ACCESS   read-only
    STATUS       current
    DESCRIPTION
        "Cisco UCS capability:Updater:pwd managed object property"
    ::= { cucsCapabilityUpdaterEntry 19 }

cucsCapabilityUpdaterRemotePath OBJECT-TYPE
    SYNTAX       SnmpAdminString
    MAX-ACCESS   read-only
    STATUS       current
    DESCRIPTION
        "Cisco UCS capability:Updater:remotePath managed object property"
    ::= { cucsCapabilityUpdaterEntry 20 }

cucsCapabilityUpdaterServer OBJECT-TYPE
    SYNTAX       SnmpAdminString
    MAX-ACCESS   read-only
    STATUS       current
    DESCRIPTION
        "Cisco UCS capability:Updater:server managed object property"
    ::= { cucsCapabilityUpdaterEntry 21 }

cucsCapabilityUpdaterUser OBJECT-TYPE
    SYNTAX       SnmpAdminString
    MAX-ACCESS   read-only
    STATUS       current
    DESCRIPTION
        "Cisco UCS capability:Updater:user managed object property"
    ::= { cucsCapabilityUpdaterEntry 22 }

cucsCapabilityUpdaterVersion OBJECT-TYPE
    SYNTAX       SnmpAdminString
    MAX-ACCESS   read-only
    STATUS       current
    DESCRIPTION
        "Cisco UCS capability:Updater:version managed object property"
    ::= { cucsCapabilityUpdaterEntry 23 }

cucsCapabilityUpdaterFsmTaskTable OBJECT-TYPE
    SYNTAX           SEQUENCE OF CucsCapabilityUpdaterFsmTaskEntry
    MAX-ACCESS       not-accessible
    STATUS           current
    DESCRIPTION
        "Cisco UCS capability:UpdaterFsmTask managed object table"
    ::= { cucsCapabilityObjects 8 }

cucsCapabilityUpdaterFsmTaskEntry OBJECT-TYPE
    SYNTAX           CucsCapabilityUpdaterFsmTaskEntry
    MAX-ACCESS       not-accessible
    STATUS           current
    DESCRIPTION
        "Entry for the cucsCapabilityUpdaterFsmTaskTable table."
    INDEX { cucsCapabilityUpdaterFsmTaskInstanceId }
    ::= { cucsCapabilityUpdaterFsmTaskTable 1 }

CucsCapabilityUpdaterFsmTaskEntry ::= SEQUENCE {
    cucsCapabilityUpdaterFsmTaskInstanceId                           CucsManagedObjectId,
    cucsCapabilityUpdaterFsmTaskDn                                   CucsManagedObjectDn,
    cucsCapabilityUpdaterFsmTaskRn                                   SnmpAdminString,
    cucsCapabilityUpdaterFsmTaskCompletion                           CucsFsmCompletion,
    cucsCapabilityUpdaterFsmTaskFlags                                CucsFsmFlags,
    cucsCapabilityUpdaterFsmTaskItem                                 CucsCapabilityUpdaterFsmTaskItem,
    cucsCapabilityUpdaterFsmTaskSeqId                                Gauge32
}

cucsCapabilityUpdaterFsmTaskInstanceId OBJECT-TYPE
    SYNTAX       CucsManagedObjectId
    MAX-ACCESS   not-accessible
    STATUS       current
    DESCRIPTION
        "Instance identifier of the managed object."
    ::= { cucsCapabilityUpdaterFsmTaskEntry 1 }

cucsCapabilityUpdaterFsmTaskDn OBJECT-TYPE
    SYNTAX       CucsManagedObjectDn
    MAX-ACCESS   read-only
    STATUS       current
    DESCRIPTION
        "Cisco UCS capability:UpdaterFsmTask:dn managed object property"
    ::= { cucsCapabilityUpdaterFsmTaskEntry 2 }

cucsCapabilityUpdaterFsmTaskRn OBJECT-TYPE
    SYNTAX       SnmpAdminString
    MAX-ACCESS   read-only
    STATUS       current
    DESCRIPTION
        "Cisco UCS capability:UpdaterFsmTask:rn managed object property"
    ::= { cucsCapabilityUpdaterFsmTaskEntry 3 }

cucsCapabilityUpdaterFsmTaskCompletion OBJECT-TYPE
    SYNTAX       CucsFsmCompletion
    MAX-ACCESS   read-only
    STATUS       current
    DESCRIPTION
        "Cisco UCS capability:UpdaterFsmTask:completion
        managed object property"
    ::= { cucsCapabilityUpdaterFsmTaskEntry 4 }

cucsCapabilityUpdaterFsmTaskFlags OBJECT-TYPE
    SYNTAX       CucsFsmFlags
    MAX-ACCESS   read-only
    STATUS       current
    DESCRIPTION
        "Cisco UCS capability:UpdaterFsmTask:flags managed
        object property"
    ::= { cucsCapabilityUpdaterFsmTaskEntry 5 }

cucsCapabilityUpdaterFsmTaskItem OBJECT-TYPE
    SYNTAX       CucsCapabilityUpdaterFsmTaskItem
    MAX-ACCESS   read-only
    STATUS       current
    DESCRIPTION
        "Cisco UCS capability:UpdaterFsmTask:item managed object property"
    ::= { cucsCapabilityUpdaterFsmTaskEntry 6 }

cucsCapabilityUpdaterFsmTaskSeqId OBJECT-TYPE
    SYNTAX       Gauge32
    MAX-ACCESS   read-only
    STATUS       current
    DESCRIPTION
        "Cisco UCS capability:UpdaterFsmTask:seqId managed
        object property"
    ::= { cucsCapabilityUpdaterFsmTaskEntry 7 }

END
