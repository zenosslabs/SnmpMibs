-- *********************************************************************
-- CISCO-UNIFIED-COMPUTING-DIAG-MIB.my
-- 
-- MIB representation of the Cisco Unified Computing System
-- DIAG management information model package
-- 
-- Created September 2011 by Charles Bullis
-- 
-- Copyright (c) 2005-2011 Cisco Systems, Inc. All rights reserved.
-- 
-- *********************************************************************

CISCO-UNIFIED-COMPUTING-DIAG-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsDiagAdminState,
    CucsDiagBladeTestType,
    CucsDiagFailureAction,
    CucsDiagNetworkTestType,
    CucsDiagSrvCtrlType,
    CucsDiagStatus,
    CucsDiagStatusIssues,
    CucsDiagSuccessAction,
    CucsDiagTestOrder,
    CucsNetworkSwitchId
        FROM CISCO-UNIFIED-COMPUTING-TC-MIB;

cucsDiagObjects MODULE-IDENTITY
    LAST-UPDATED    "201109150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        DIAG management information model package"
    ::= { ciscoUnifiedComputingMIBObjects 12 }

cucsDiagBladeTestTable OBJECT-TYPE
    SYNTAX           SEQUENCE OF CucsDiagBladeTestEntry
    MAX-ACCESS       not-accessible
    STATUS           current
    DESCRIPTION
        "Cisco UCS diag:BladeTest managed object table"
    ::= { cucsDiagObjects 1 }

cucsDiagBladeTestEntry OBJECT-TYPE
    SYNTAX           CucsDiagBladeTestEntry
    MAX-ACCESS       not-accessible
    STATUS           current
    DESCRIPTION
        "Entry for the cucsDiagBladeTestTable table."
    INDEX { cucsDiagBladeTestInstanceId }
    ::= { cucsDiagBladeTestTable 1 }

CucsDiagBladeTestEntry ::= SEQUENCE {
    cucsDiagBladeTestInstanceId                                      CucsManagedObjectId,
    cucsDiagBladeTestDn                                              CucsManagedObjectDn,
    cucsDiagBladeTestRn                                              SnmpAdminString,
    cucsDiagBladeTestLength                                          Gauge32,
    cucsDiagBladeTestOrder                                           CucsDiagTestOrder,
    cucsDiagBladeTestType                                            CucsDiagBladeTestType
}

cucsDiagBladeTestInstanceId OBJECT-TYPE
    SYNTAX       CucsManagedObjectId
    MAX-ACCESS   not-accessible
    STATUS       current
    DESCRIPTION
        "Instance identifier of the managed object."
    ::= { cucsDiagBladeTestEntry 1 }

cucsDiagBladeTestDn OBJECT-TYPE
    SYNTAX       CucsManagedObjectDn
    MAX-ACCESS   read-only
    STATUS       current
    DESCRIPTION
        "Cisco UCS diag:BladeTest:dn managed object property"
    ::= { cucsDiagBladeTestEntry 2 }

cucsDiagBladeTestRn OBJECT-TYPE
    SYNTAX       SnmpAdminString
    MAX-ACCESS   read-only
    STATUS       current
    DESCRIPTION
        "Cisco UCS diag:BladeTest:rn managed object property"
    ::= { cucsDiagBladeTestEntry 3 }

cucsDiagBladeTestLength OBJECT-TYPE
    SYNTAX       Gauge32
    MAX-ACCESS   read-only
    STATUS       current
    DESCRIPTION
        "Cisco UCS diag:BladeTest:length managed object property"
    ::= { cucsDiagBladeTestEntry 4 }

cucsDiagBladeTestOrder OBJECT-TYPE
    SYNTAX       CucsDiagTestOrder
    MAX-ACCESS   read-only
    STATUS       current
    DESCRIPTION
        "Cisco UCS diag:BladeTest:order managed object property"
    ::= { cucsDiagBladeTestEntry 5 }

cucsDiagBladeTestType OBJECT-TYPE
    SYNTAX       CucsDiagBladeTestType
    MAX-ACCESS   read-only
    STATUS       current
    DESCRIPTION
        "Cisco UCS diag:BladeTest:type managed object property"
    ::= { cucsDiagBladeTestEntry 6 }

cucsDiagNetworkTestTable OBJECT-TYPE
    SYNTAX           SEQUENCE OF CucsDiagNetworkTestEntry
    MAX-ACCESS       not-accessible
    STATUS           current
    DESCRIPTION
        "Cisco UCS diag:NetworkTest managed object table"
    ::= { cucsDiagObjects 2 }

cucsDiagNetworkTestEntry OBJECT-TYPE
    SYNTAX           CucsDiagNetworkTestEntry
    MAX-ACCESS       not-accessible
    STATUS           current
    DESCRIPTION
        "Entry for the cucsDiagNetworkTestTable table."
    INDEX { cucsDiagNetworkTestInstanceId }
    ::= { cucsDiagNetworkTestTable 1 }

CucsDiagNetworkTestEntry ::= SEQUENCE {
    cucsDiagNetworkTestInstanceId                                    CucsManagedObjectId,
    cucsDiagNetworkTestDn                                            CucsManagedObjectDn,
    cucsDiagNetworkTestRn                                            SnmpAdminString,
    cucsDiagNetworkTestLength                                        Gauge32,
    cucsDiagNetworkTestOrder                                         CucsDiagTestOrder,
    cucsDiagNetworkTestSwitchId                                      CucsNetworkSwitchId,
    cucsDiagNetworkTestType                                          CucsDiagNetworkTestType
}

cucsDiagNetworkTestInstanceId OBJECT-TYPE
    SYNTAX       CucsManagedObjectId
    MAX-ACCESS   not-accessible
    STATUS       current
    DESCRIPTION
        "Instance identifier of the managed object."
    ::= { cucsDiagNetworkTestEntry 1 }

cucsDiagNetworkTestDn OBJECT-TYPE
    SYNTAX       CucsManagedObjectDn
    MAX-ACCESS   read-only
    STATUS       current
    DESCRIPTION
        "Cisco UCS diag:NetworkTest:dn managed object property"
    ::= { cucsDiagNetworkTestEntry 2 }

cucsDiagNetworkTestRn OBJECT-TYPE
    SYNTAX       SnmpAdminString
    MAX-ACCESS   read-only
    STATUS       current
    DESCRIPTION
        "Cisco UCS diag:NetworkTest:rn managed object property"
    ::= { cucsDiagNetworkTestEntry 3 }

cucsDiagNetworkTestLength OBJECT-TYPE
    SYNTAX       Gauge32
    MAX-ACCESS   read-only
    STATUS       current
    DESCRIPTION
        "Cisco UCS diag:NetworkTest:length managed object property"
    ::= { cucsDiagNetworkTestEntry 4 }

cucsDiagNetworkTestOrder OBJECT-TYPE
    SYNTAX       CucsDiagTestOrder
    MAX-ACCESS   read-only
    STATUS       current
    DESCRIPTION
        "Cisco UCS diag:NetworkTest:order managed object property"
    ::= { cucsDiagNetworkTestEntry 5 }

cucsDiagNetworkTestSwitchId OBJECT-TYPE
    SYNTAX       CucsNetworkSwitchId
    MAX-ACCESS   read-only
    STATUS       current
    DESCRIPTION
        "Cisco UCS diag:NetworkTest:switchId managed object property"
    ::= { cucsDiagNetworkTestEntry 6 }

cucsDiagNetworkTestType OBJECT-TYPE
    SYNTAX       CucsDiagNetworkTestType
    MAX-ACCESS   read-only
    STATUS       current
    DESCRIPTION
        "Cisco UCS diag:NetworkTest:type managed object property"
    ::= { cucsDiagNetworkTestEntry 7 }

cucsDiagRsltTable OBJECT-TYPE
    SYNTAX           SEQUENCE OF CucsDiagRsltEntry
    MAX-ACCESS       not-accessible
    STATUS           current
    DESCRIPTION
        "Cisco UCS diag:Rslt managed object table"
    ::= { cucsDiagObjects 3 }

cucsDiagRsltEntry OBJECT-TYPE
    SYNTAX           CucsDiagRsltEntry
    MAX-ACCESS       not-accessible
    STATUS           current
    DESCRIPTION
        "Entry for the cucsDiagRsltTable table."
    INDEX { cucsDiagRsltInstanceId }
    ::= { cucsDiagRsltTable 1 }

CucsDiagRsltEntry ::= SEQUENCE {
    cucsDiagRsltInstanceId                                           CucsManagedObjectId,
    cucsDiagRsltDn                                                   CucsManagedObjectDn,
    cucsDiagRsltRn                                                   SnmpAdminString,
    cucsDiagRsltDescr                                                SnmpAdminString,
    cucsDiagRsltEndTs                                                DateAndTime,
    cucsDiagRsltId                                                   Gauge32,
    cucsDiagRsltResult                                               Gauge32,
    cucsDiagRsltRsltStatus                                           CucsDiagStatus,
    cucsDiagRsltStartTs                                              DateAndTime
}

cucsDiagRsltInstanceId OBJECT-TYPE
    SYNTAX       CucsManagedObjectId
    MAX-ACCESS   not-accessible
    STATUS       current
    DESCRIPTION
        "Instance identifier of the managed object."
    ::= { cucsDiagRsltEntry 1 }

cucsDiagRsltDn OBJECT-TYPE
    SYNTAX       CucsManagedObjectDn
    MAX-ACCESS   read-only
    STATUS       current
    DESCRIPTION
        "Cisco UCS diag:Rslt:dn managed object property"
    ::= { cucsDiagRsltEntry 2 }

cucsDiagRsltRn OBJECT-TYPE
    SYNTAX       SnmpAdminString
    MAX-ACCESS   read-only
    STATUS       current
    DESCRIPTION
        "Cisco UCS diag:Rslt:rn managed object property"
    ::= { cucsDiagRsltEntry 3 }

cucsDiagRsltDescr OBJECT-TYPE
    SYNTAX       SnmpAdminString
    MAX-ACCESS   read-only
    STATUS       current
    DESCRIPTION
        "Cisco UCS diag:Rslt:descr managed object property"
    ::= { cucsDiagRsltEntry 4 }

cucsDiagRsltEndTs OBJECT-TYPE
    SYNTAX       DateAndTime
    MAX-ACCESS   read-only
    STATUS       current
    DESCRIPTION
        "Cisco UCS diag:Rslt:endTs managed object property"
    ::= { cucsDiagRsltEntry 5 }

cucsDiagRsltId OBJECT-TYPE
    SYNTAX       Gauge32
    MAX-ACCESS   read-only
    STATUS       current
    DESCRIPTION
        "Cisco UCS diag:Rslt:id managed object property"
    ::= { cucsDiagRsltEntry 6 }

cucsDiagRsltResult OBJECT-TYPE
    SYNTAX       Gauge32
    MAX-ACCESS   read-only
    STATUS       current
    DESCRIPTION
        "Cisco UCS diag:Rslt:result managed object property"
    ::= { cucsDiagRsltEntry 7 }

cucsDiagRsltRsltStatus OBJECT-TYPE
    SYNTAX       CucsDiagStatus
    MAX-ACCESS   read-only
    STATUS       current
    DESCRIPTION
        "Cisco UCS diag:Rslt:rsltStatus managed object property"
    ::= { cucsDiagRsltEntry 8 }

cucsDiagRsltStartTs OBJECT-TYPE
    SYNTAX       DateAndTime
    MAX-ACCESS   read-only
    STATUS       current
    DESCRIPTION
        "Cisco UCS diag:Rslt:startTs managed object property"
    ::= { cucsDiagRsltEntry 9 }

cucsDiagRunPolicyTable OBJECT-TYPE
    SYNTAX           SEQUENCE OF CucsDiagRunPolicyEntry
    MAX-ACCESS       not-accessible
    STATUS           current
    DESCRIPTION
        "Cisco UCS diag:RunPolicy managed object table"
    ::= { cucsDiagObjects 4 }

cucsDiagRunPolicyEntry OBJECT-TYPE
    SYNTAX           CucsDiagRunPolicyEntry
    MAX-ACCESS       not-accessible
    STATUS           current
    DESCRIPTION
        "Entry for the cucsDiagRunPolicyTable table."
    INDEX { cucsDiagRunPolicyInstanceId }
    ::= { cucsDiagRunPolicyTable 1 }

CucsDiagRunPolicyEntry ::= SEQUENCE {
    cucsDiagRunPolicyInstanceId                                      CucsManagedObjectId,
    cucsDiagRunPolicyDn                                              CucsManagedObjectDn,
    cucsDiagRunPolicyRn                                              SnmpAdminString,
    cucsDiagRunPolicyDescr                                           SnmpAdminString,
    cucsDiagRunPolicyFailureAction                                   CucsDiagFailureAction,
    cucsDiagRunPolicyIntId                                           SnmpAdminString,
    cucsDiagRunPolicyName                                            SnmpAdminString,
    cucsDiagRunPolicySuccessAction                                   CucsDiagSuccessAction
}

cucsDiagRunPolicyInstanceId OBJECT-TYPE
    SYNTAX       CucsManagedObjectId
    MAX-ACCESS   not-accessible
    STATUS       current
    DESCRIPTION
        "Instance identifier of the managed object."
    ::= { cucsDiagRunPolicyEntry 1 }

cucsDiagRunPolicyDn OBJECT-TYPE
    SYNTAX       CucsManagedObjectDn
    MAX-ACCESS   read-only
    STATUS       current
    DESCRIPTION
        "Cisco UCS diag:RunPolicy:dn managed object property"
    ::= { cucsDiagRunPolicyEntry 2 }

cucsDiagRunPolicyRn OBJECT-TYPE
    SYNTAX       SnmpAdminString
    MAX-ACCESS   read-only
    STATUS       current
    DESCRIPTION
        "Cisco UCS diag:RunPolicy:rn managed object property"
    ::= { cucsDiagRunPolicyEntry 3 }

cucsDiagRunPolicyDescr OBJECT-TYPE
    SYNTAX       SnmpAdminString
    MAX-ACCESS   read-only
    STATUS       current
    DESCRIPTION
        "Cisco UCS diag:RunPolicy:descr managed object property"
    ::= { cucsDiagRunPolicyEntry 4 }

cucsDiagRunPolicyFailureAction OBJECT-TYPE
    SYNTAX       CucsDiagFailureAction
    MAX-ACCESS   read-only
    STATUS       current
    DESCRIPTION
        "Cisco UCS diag:RunPolicy:failureAction managed object property"
    ::= { cucsDiagRunPolicyEntry 5 }

cucsDiagRunPolicyIntId OBJECT-TYPE
    SYNTAX       SnmpAdminString
    MAX-ACCESS   read-only
    STATUS       current
    DESCRIPTION
        "Cisco UCS diag:RunPolicy:intId managed object property"
    ::= { cucsDiagRunPolicyEntry 6 }

cucsDiagRunPolicyName OBJECT-TYPE
    SYNTAX       SnmpAdminString
    MAX-ACCESS   read-only
    STATUS       current
    DESCRIPTION
        "Cisco UCS diag:RunPolicy:name managed object property"
    ::= { cucsDiagRunPolicyEntry 7 }

cucsDiagRunPolicySuccessAction OBJECT-TYPE
    SYNTAX       CucsDiagSuccessAction
    MAX-ACCESS   read-only
    STATUS       current
    DESCRIPTION
        "Cisco UCS diag:RunPolicy:successAction managed object property"
    ::= { cucsDiagRunPolicyEntry 8 }

cucsDiagSrvCapProviderTable OBJECT-TYPE
    SYNTAX           SEQUENCE OF CucsDiagSrvCapProviderEntry
    MAX-ACCESS       not-accessible
    STATUS           current
    DESCRIPTION
        "Cisco UCS diag:SrvCapProvider managed object table"
    ::= { cucsDiagObjects 5 }

cucsDiagSrvCapProviderEntry OBJECT-TYPE
    SYNTAX           CucsDiagSrvCapProviderEntry
    MAX-ACCESS       not-accessible
    STATUS           current
    DESCRIPTION
        "Entry for the cucsDiagSrvCapProviderTable table."
    INDEX { cucsDiagSrvCapProviderInstanceId }
    ::= { cucsDiagSrvCapProviderTable 1 }

CucsDiagSrvCapProviderEntry ::= SEQUENCE {
    cucsDiagSrvCapProviderInstanceId                                 CucsManagedObjectId,
    cucsDiagSrvCapProviderDn                                         CucsManagedObjectDn,
    cucsDiagSrvCapProviderRn                                         SnmpAdminString,
    cucsDiagSrvCapProviderDeprecated                                 TruthValue,
    cucsDiagSrvCapProviderGencount                                   Gauge32,
    cucsDiagSrvCapProviderMgmtPlaneVer                               SnmpAdminString,
    cucsDiagSrvCapProviderModel                                      SnmpAdminString,
    cucsDiagSrvCapProviderRevision                                   SnmpAdminString,
    cucsDiagSrvCapProviderVendor                                     SnmpAdminString,
    cucsDiagSrvCapProviderPromCardType                               Gauge32,
    cucsDiagSrvCapProviderDeleted                                    TruthValue
}

cucsDiagSrvCapProviderInstanceId OBJECT-TYPE
    SYNTAX       CucsManagedObjectId
    MAX-ACCESS   not-accessible
    STATUS       current
    DESCRIPTION
        "Instance identifier of the managed object."
    ::= { cucsDiagSrvCapProviderEntry 1 }

cucsDiagSrvCapProviderDn OBJECT-TYPE
    SYNTAX       CucsManagedObjectDn
    MAX-ACCESS   read-only
    STATUS       current
    DESCRIPTION
        "Cisco UCS diag:SrvCapProvider:dn managed object property"
    ::= { cucsDiagSrvCapProviderEntry 2 }

cucsDiagSrvCapProviderRn OBJECT-TYPE
    SYNTAX       SnmpAdminString
    MAX-ACCESS   read-only
    STATUS       current
    DESCRIPTION
        "Cisco UCS diag:SrvCapProvider:rn managed object property"
    ::= { cucsDiagSrvCapProviderEntry 3 }

cucsDiagSrvCapProviderDeprecated OBJECT-TYPE
    SYNTAX       TruthValue
    MAX-ACCESS   read-only
    STATUS       current
    DESCRIPTION
        "Cisco UCS diag:SrvCapProvider:deprecated managed object property"
    ::= { cucsDiagSrvCapProviderEntry 4 }

cucsDiagSrvCapProviderGencount OBJECT-TYPE
    SYNTAX       Gauge32
    MAX-ACCESS   read-only
    STATUS       current
    DESCRIPTION
        "Cisco UCS diag:SrvCapProvider:gencount managed object property"
    ::= { cucsDiagSrvCapProviderEntry 5 }

cucsDiagSrvCapProviderMgmtPlaneVer OBJECT-TYPE
    SYNTAX       SnmpAdminString
    MAX-ACCESS   read-only
    STATUS       current
    DESCRIPTION
        "Cisco UCS diag:SrvCapProvider:mgmtPlaneVer managed
        object property"
    ::= { cucsDiagSrvCapProviderEntry 6 }

cucsDiagSrvCapProviderModel OBJECT-TYPE
    SYNTAX       SnmpAdminString
    MAX-ACCESS   read-only
    STATUS       current
    DESCRIPTION
        "Cisco UCS diag:SrvCapProvider:model managed object property"
    ::= { cucsDiagSrvCapProviderEntry 7 }

cucsDiagSrvCapProviderRevision OBJECT-TYPE
    SYNTAX       SnmpAdminString
    MAX-ACCESS   read-only
    STATUS       current
    DESCRIPTION
        "Cisco UCS diag:SrvCapProvider:revision managed object property"
    ::= { cucsDiagSrvCapProviderEntry 8 }

cucsDiagSrvCapProviderVendor OBJECT-TYPE
    SYNTAX       SnmpAdminString
    MAX-ACCESS   read-only
    STATUS       current
    DESCRIPTION
        "Cisco UCS diag:SrvCapProvider:vendor managed object property"
    ::= { cucsDiagSrvCapProviderEntry 9 }

cucsDiagSrvCapProviderPromCardType OBJECT-TYPE
    SYNTAX       Gauge32
    MAX-ACCESS   read-only
    STATUS       current
    DESCRIPTION
        "Cisco UCS diag:SrvCapProvider:promCardType managed
        object property"
    ::= { cucsDiagSrvCapProviderEntry 10 }

cucsDiagSrvCapProviderDeleted OBJECT-TYPE
    SYNTAX       TruthValue
    MAX-ACCESS   read-only
    STATUS       current
    DESCRIPTION
        "Cisco UCS diag:SrvCapProvider:deleted managed object property"
    ::= { cucsDiagSrvCapProviderEntry 11 }

cucsDiagSrvCtrlTable OBJECT-TYPE
    SYNTAX           SEQUENCE OF CucsDiagSrvCtrlEntry
    MAX-ACCESS       not-accessible
    STATUS           current
    DESCRIPTION
        "Cisco UCS diag:SrvCtrl managed object table"
    ::= { cucsDiagObjects 6 }

cucsDiagSrvCtrlEntry OBJECT-TYPE
    SYNTAX           CucsDiagSrvCtrlEntry
    MAX-ACCESS       not-accessible
    STATUS           current
    DESCRIPTION
        "Entry for the cucsDiagSrvCtrlTable table."
    INDEX { cucsDiagSrvCtrlInstanceId }
    ::= { cucsDiagSrvCtrlTable 1 }

CucsDiagSrvCtrlEntry ::= SEQUENCE {
    cucsDiagSrvCtrlInstanceId                                        CucsManagedObjectId,
    cucsDiagSrvCtrlDn                                                CucsManagedObjectDn,
    cucsDiagSrvCtrlRn                                                SnmpAdminString,
    cucsDiagSrvCtrlAdminState                                        CucsDiagAdminState,
    cucsDiagSrvCtrlImgLoc                                            SnmpAdminString,
    cucsDiagSrvCtrlImgName                                           SnmpAdminString,
    cucsDiagSrvCtrlOperQualifier                                     CucsDiagStatusIssues,
    cucsDiagSrvCtrlOperState                                         CucsDiagStatus,
    cucsDiagSrvCtrlRunPolicyName                                     SnmpAdminString,
    cucsDiagSrvCtrlType                                              CucsDiagSrvCtrlType,
    cucsDiagSrvCtrlEndTs                                             DateAndTime,
    cucsDiagSrvCtrlEndTsM                                            Unsigned64,
    cucsDiagSrvCtrlErrorDescr                                        SnmpAdminString,
    cucsDiagSrvCtrlStartTs                                           DateAndTime,
    cucsDiagSrvCtrlStartTsM                                          Unsigned64
}

cucsDiagSrvCtrlInstanceId OBJECT-TYPE
    SYNTAX       CucsManagedObjectId
    MAX-ACCESS   not-accessible
    STATUS       current
    DESCRIPTION
        "Instance identifier of the managed object."
    ::= { cucsDiagSrvCtrlEntry 1 }

cucsDiagSrvCtrlDn OBJECT-TYPE
    SYNTAX       CucsManagedObjectDn
    MAX-ACCESS   read-only
    STATUS       current
    DESCRIPTION
        "Cisco UCS diag:SrvCtrl:dn managed object property"
    ::= { cucsDiagSrvCtrlEntry 2 }

cucsDiagSrvCtrlRn OBJECT-TYPE
    SYNTAX       SnmpAdminString
    MAX-ACCESS   read-only
    STATUS       current
    DESCRIPTION
        "Cisco UCS diag:SrvCtrl:rn managed object property"
    ::= { cucsDiagSrvCtrlEntry 3 }

cucsDiagSrvCtrlAdminState OBJECT-TYPE
    SYNTAX       CucsDiagAdminState
    MAX-ACCESS   read-only
    STATUS       current
    DESCRIPTION
        "Cisco UCS diag:SrvCtrl:adminState managed object property"
    ::= { cucsDiagSrvCtrlEntry 4 }

cucsDiagSrvCtrlImgLoc OBJECT-TYPE
    SYNTAX       SnmpAdminString
    MAX-ACCESS   read-only
    STATUS       current
    DESCRIPTION
        "Cisco UCS diag:SrvCtrl:imgLoc managed object property"
    ::= { cucsDiagSrvCtrlEntry 5 }

cucsDiagSrvCtrlImgName OBJECT-TYPE
    SYNTAX       SnmpAdminString
    MAX-ACCESS   read-only
    STATUS       current
    DESCRIPTION
        "Cisco UCS diag:SrvCtrl:imgName managed object property"
    ::= { cucsDiagSrvCtrlEntry 6 }

cucsDiagSrvCtrlOperQualifier OBJECT-TYPE
    SYNTAX       CucsDiagStatusIssues
    MAX-ACCESS   read-only
    STATUS       current
    DESCRIPTION
        "Cisco UCS diag:SrvCtrl:operQualifier managed object property"
    ::= { cucsDiagSrvCtrlEntry 7 }

cucsDiagSrvCtrlOperState OBJECT-TYPE
    SYNTAX       CucsDiagStatus
    MAX-ACCESS   read-only
    STATUS       current
    DESCRIPTION
        "Cisco UCS diag:SrvCtrl:operState managed object property"
    ::= { cucsDiagSrvCtrlEntry 8 }

cucsDiagSrvCtrlRunPolicyName OBJECT-TYPE
    SYNTAX       SnmpAdminString
    MAX-ACCESS   read-only
    STATUS       current
    DESCRIPTION
        "Cisco UCS diag:SrvCtrl:runPolicyName managed object property"
    ::= { cucsDiagSrvCtrlEntry 9 }

cucsDiagSrvCtrlType OBJECT-TYPE
    SYNTAX       CucsDiagSrvCtrlType
    MAX-ACCESS   read-only
    STATUS       current
    DESCRIPTION
        "Cisco UCS diag:SrvCtrl:type managed object property"
    ::= { cucsDiagSrvCtrlEntry 10 }

cucsDiagSrvCtrlEndTs OBJECT-TYPE
    SYNTAX       DateAndTime
    MAX-ACCESS   read-only
    STATUS       current
    DESCRIPTION
        "Cisco UCS diag:SrvCtrl:endTs managed object property"
    ::= { cucsDiagSrvCtrlEntry 11 }

cucsDiagSrvCtrlEndTsM OBJECT-TYPE
    SYNTAX       Unsigned64
    MAX-ACCESS   read-only
    STATUS       current
    DESCRIPTION
        "Cisco UCS diag:SrvCtrl:endTsM managed object property"
    ::= { cucsDiagSrvCtrlEntry 12 }

cucsDiagSrvCtrlErrorDescr OBJECT-TYPE
    SYNTAX       SnmpAdminString
    MAX-ACCESS   read-only
    STATUS       current
    DESCRIPTION
        "Cisco UCS diag:SrvCtrl:errorDescr managed object property"
    ::= { cucsDiagSrvCtrlEntry 13 }

cucsDiagSrvCtrlStartTs OBJECT-TYPE
    SYNTAX       DateAndTime
    MAX-ACCESS   read-only
    STATUS       current
    DESCRIPTION
        "Cisco UCS diag:SrvCtrl:startTs managed object property"
    ::= { cucsDiagSrvCtrlEntry 14 }

cucsDiagSrvCtrlStartTsM OBJECT-TYPE
    SYNTAX       Unsigned64
    MAX-ACCESS   read-only
    STATUS       current
    DESCRIPTION
        "Cisco UCS diag:SrvCtrl:startTsM managed object property"
    ::= { cucsDiagSrvCtrlEntry 15 }

END
