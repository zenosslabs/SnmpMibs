-- *********************************************************************
-- CISCO-UNIFIED-COMPUTING-SYSDEBUG-MIB.my
-- 
-- MIB representation of the Cisco Unified Computing System
-- SYSDEBUG management information model package
-- 
-- Created September 2011 by Charles Bullis
-- 
-- Copyright (c) 2005-2011 Cisco Systems, Inc. All rights reserved.
-- 
-- *********************************************************************

CISCO-UNIFIED-COMPUTING-SYSDEBUG-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsCommClientAdminState,
    CucsConditionRemoteInvRslt,
    CucsFsmCompletion,
    CucsFsmFlags,
    CucsNetworkSwitchId,
    CucsSysdebugAutoCoreFileExportTargetFsmTaskItem,
    CucsSysdebugAutoCoreFileExportTargetProto,
    CucsSysdebugBackupBehaviorInterval,
    CucsSysdebugBackupBehaviorProto,
    CucsSysdebugBackupFormat,
    CucsSysdebugCoreExportStatus,
    CucsSysdebugCoreFileAdminState,
    CucsSysdebugCoreFileOperState,
    CucsSysdebugCoreFsmTaskItem,
    CucsSysdebugEpLogAdminState,
    CucsSysdebugEpLogBackupAction,
    CucsSysdebugEpLogCapacity,
    CucsSysdebugEpLogType,
    CucsSysdebugLogControlDomainEnum,
    CucsSysdebugLogControlEpFsmTaskItem,
    CucsSysdebugLogControlLevel,
    CucsSysdebugMEpLogOperState,
    CucsSysdebugManualCoreFileExportTargetAdminState,
    CucsSysdebugManualCoreFileExportTargetFsmTaskItem,
    CucsSysdebugManualCoreFileExportTargetProto,
    CucsSysdebugTSCmdOptMajorType,
    CucsSysdebugTechSupportAdminState,
    CucsSysdebugTechSupportFsmTaskItem,
    CucsSysdebugTechSupportOperState,
    CucsSysfileExporterPostAction
        FROM CISCO-UNIFIED-COMPUTING-TC-MIB;

cucsSysdebugObjects MODULE-IDENTITY
    LAST-UPDATED    "201109150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        SYSDEBUG management information model package"
    ::= { ciscoUnifiedComputingMIBObjects 47 }

cucsSysdebugAutoCoreFileExportTargetTable OBJECT-TYPE
    SYNTAX           SEQUENCE OF CucsSysdebugAutoCoreFileExportTargetEntry
    MAX-ACCESS       not-accessible
    STATUS           current
    DESCRIPTION
        "Cisco UCS sysdebug:AutoCoreFileExportTarget managed object table"
    ::= { cucsSysdebugObjects 1 }

cucsSysdebugAutoCoreFileExportTargetEntry OBJECT-TYPE
    SYNTAX           CucsSysdebugAutoCoreFileExportTargetEntry
    MAX-ACCESS       not-accessible
    STATUS           current
    DESCRIPTION
        "Entry for the cucsSysdebugAutoCoreFileExportTargetTable table."
    INDEX { cucsSysdebugAutoCoreFileExportTargetInstanceId }
    ::= { cucsSysdebugAutoCoreFileExportTargetTable 1 }

CucsSysdebugAutoCoreFileExportTargetEntry ::= SEQUENCE {
    cucsSysdebugAutoCoreFileExportTargetInstanceId                   CucsManagedObjectId,
    cucsSysdebugAutoCoreFileExportTargetDn                           CucsManagedObjectDn,
    cucsSysdebugAutoCoreFileExportTargetRn                           SnmpAdminString,
    cucsSysdebugAutoCoreFileExportTargetAdminState                   CucsCommClientAdminState,
    cucsSysdebugAutoCoreFileExportTargetDescr                        SnmpAdminString,
    cucsSysdebugAutoCoreFileExportTargetFsmDescr                     SnmpAdminString,
    cucsSysdebugAutoCoreFileExportTargetFsmPrev                      SnmpAdminString,
    cucsSysdebugAutoCoreFileExportTargetFsmProgr                     Gauge32,
    cucsSysdebugAutoCoreFileExportTargetFsmRmtInvErrCode             Gauge32,
    cucsSysdebugAutoCoreFileExportTargetFsmRmtInvErrDescr            SnmpAdminString,
    cucsSysdebugAutoCoreFileExportTargetFsmRmtInvRslt                CucsConditionRemoteInvRslt,
    cucsSysdebugAutoCoreFileExportTargetFsmStageDescr                SnmpAdminString,
    cucsSysdebugAutoCoreFileExportTargetFsmStamp                     DateAndTime,
    cucsSysdebugAutoCoreFileExportTargetFsmStatus                    SnmpAdminString,
    cucsSysdebugAutoCoreFileExportTargetFsmTry                       Gauge32,
    cucsSysdebugAutoCoreFileExportTargetHostname                     SnmpAdminString,
    cucsSysdebugAutoCoreFileExportTargetIntId                        SnmpAdminString,
    cucsSysdebugAutoCoreFileExportTargetName                         SnmpAdminString,
    cucsSysdebugAutoCoreFileExportTargetPath                         SnmpAdminString,
    cucsSysdebugAutoCoreFileExportTargetPort                         Gauge32,
    cucsSysdebugAutoCoreFileExportTargetPostAction                   CucsSysfileExporterPostAction,
    cucsSysdebugAutoCoreFileExportTargetProto                        CucsSysdebugAutoCoreFileExportTargetProto,
    cucsSysdebugAutoCoreFileExportTargetExportFailureReason          SnmpAdminString,
    cucsSysdebugAutoCoreFileExportTargetExportStatus                 CucsSysdebugCoreExportStatus
}

cucsSysdebugAutoCoreFileExportTargetInstanceId OBJECT-TYPE
    SYNTAX       CucsManagedObjectId
    MAX-ACCESS   not-accessible
    STATUS       current
    DESCRIPTION
        "Instance identifier of the managed object."
    ::= { cucsSysdebugAutoCoreFileExportTargetEntry 1 }

cucsSysdebugAutoCoreFileExportTargetDn OBJECT-TYPE
    SYNTAX       CucsManagedObjectDn
    MAX-ACCESS   read-only
    STATUS       current
    DESCRIPTION
        "Cisco UCS sysdebug:AutoCoreFileExportTarget:dn
        managed object property"
    ::= { cucsSysdebugAutoCoreFileExportTargetEntry 2 }

cucsSysdebugAutoCoreFileExportTargetRn OBJECT-TYPE
    SYNTAX       SnmpAdminString
    MAX-ACCESS   read-only
    STATUS       current
    DESCRIPTION
        "Cisco UCS sysdebug:AutoCoreFileExportTarget:rn
        managed object property"
    ::= { cucsSysdebugAutoCoreFileExportTargetEntry 3 }

cucsSysdebugAutoCoreFileExportTargetAdminState OBJECT-TYPE
    SYNTAX       CucsCommClientAdminState
    MAX-ACCESS   read-only
    STATUS       current
    DESCRIPTION
        "Cisco UCS sysdebug:AutoCoreFileExportTarget:adminState
        managed object property"
    ::= { cucsSysdebugAutoCoreFileExportTargetEntry 4 }

cucsSysdebugAutoCoreFileExportTargetDescr OBJECT-TYPE
    SYNTAX       SnmpAdminString
    MAX-ACCESS   read-only
    STATUS       current
    DESCRIPTION
        "Cisco UCS sysdebug:AutoCoreFileExportTarget:descr
        managed object property"
    ::= { cucsSysdebugAutoCoreFileExportTargetEntry 5 }

cucsSysdebugAutoCoreFileExportTargetFsmDescr OBJECT-TYPE
    SYNTAX       SnmpAdminString
    MAX-ACCESS   read-only
    STATUS       current
    DESCRIPTION
        "Cisco UCS sysdebug:AutoCoreFileExportTarget:fsmDescr
        managed object property"
    ::= { cucsSysdebugAutoCoreFileExportTargetEntry 6 }

cucsSysdebugAutoCoreFileExportTargetFsmPrev OBJECT-TYPE
    SYNTAX       SnmpAdminString
    MAX-ACCESS   read-only
    STATUS       current
    DESCRIPTION
        "Cisco UCS sysdebug:AutoCoreFileExportTarget:fsmPrev
        managed object property"
    ::= { cucsSysdebugAutoCoreFileExportTargetEntry 7 }

cucsSysdebugAutoCoreFileExportTargetFsmProgr OBJECT-TYPE
    SYNTAX       Gauge32
    MAX-ACCESS   read-only
    STATUS       current
    DESCRIPTION
        "Cisco UCS sysdebug:AutoCoreFileExportTarget:fsmProgr
        managed object property"
    ::= { cucsSysdebugAutoCoreFileExportTargetEntry 8 }

cucsSysdebugAutoCoreFileExportTargetFsmRmtInvErrCode OBJECT-TYPE
    SYNTAX       Gauge32
    MAX-ACCESS   read-only
    STATUS       current
    DESCRIPTION
        "Cisco UCS sysdebug:AutoCoreFileExportTarget:fsmRmtInvErrCode
        managed object property"
    ::= { cucsSysdebugAutoCoreFileExportTargetEntry 9 }

cucsSysdebugAutoCoreFileExportTargetFsmRmtInvErrDescr OBJECT-TYPE
    SYNTAX       SnmpAdminString
    MAX-ACCESS   read-only
    STATUS       current
    DESCRIPTION
        "Cisco UCS sysdebug:AutoCoreFileExportTarget:fsmRmtInvErrDescr
        managed object property"
    ::= { cucsSysdebugAutoCoreFileExportTargetEntry 10 }

cucsSysdebugAutoCoreFileExportTargetFsmRmtInvRslt OBJECT-TYPE
    SYNTAX       CucsConditionRemoteInvRslt
    MAX-ACCESS   read-only
    STATUS       current
    DESCRIPTION
        "Cisco UCS sysdebug:AutoCoreFileExportTarget:fsmRmtInvRslt
        managed object property"
    ::= { cucsSysdebugAutoCoreFileExportTargetEntry 11 }

cucsSysdebugAutoCoreFileExportTargetFsmStageDescr OBJECT-TYPE
    SYNTAX       SnmpAdminString
    MAX-ACCESS   read-only
    STATUS       current
    DESCRIPTION
        "Cisco UCS sysdebug:AutoCoreFileExportTarget:fsmStageDescr
        managed object property"
    ::= { cucsSysdebugAutoCoreFileExportTargetEntry 12 }

cucsSysdebugAutoCoreFileExportTargetFsmStamp OBJECT-TYPE
    SYNTAX       DateAndTime
    MAX-ACCESS   read-only
    STATUS       current
    DESCRIPTION
        "Cisco UCS sysdebug:AutoCoreFileExportTarget:fsmStamp
        managed object property"
    ::= { cucsSysdebugAutoCoreFileExportTargetEntry 13 }

cucsSysdebugAutoCoreFileExportTargetFsmStatus OBJECT-TYPE
    SYNTAX       SnmpAdminString
    MAX-ACCESS   read-only
    STATUS       current
    DESCRIPTION
        "Cisco UCS sysdebug:AutoCoreFileExportTarget:fsmStatus
        managed object property"
    ::= { cucsSysdebugAutoCoreFileExportTargetEntry 14 }

cucsSysdebugAutoCoreFileExportTargetFsmTry OBJECT-TYPE
    SYNTAX       Gauge32
    MAX-ACCESS   read-only
    STATUS       current
    DESCRIPTION
        "Cisco UCS sysdebug:AutoCoreFileExportTarget:fsmTry
        managed object property"
    ::= { cucsSysdebugAutoCoreFileExportTargetEntry 15 }

cucsSysdebugAutoCoreFileExportTargetHostname OBJECT-TYPE
    SYNTAX       SnmpAdminString
    MAX-ACCESS   read-only
    STATUS       current
    DESCRIPTION
        "Cisco UCS sysdebug:AutoCoreFileExportTarget:hostname
        managed object property"
    ::= { cucsSysdebugAutoCoreFileExportTargetEntry 16 }

cucsSysdebugAutoCoreFileExportTargetIntId OBJECT-TYPE
    SYNTAX       SnmpAdminString
    MAX-ACCESS   read-only
    STATUS       current
    DESCRIPTION
        "Cisco UCS sysdebug:AutoCoreFileExportTarget:intId
        managed object property"
    ::= { cucsSysdebugAutoCoreFileExportTargetEntry 17 }

cucsSysdebugAutoCoreFileExportTargetName OBJECT-TYPE
    SYNTAX       SnmpAdminString
    MAX-ACCESS   read-only
    STATUS       current
    DESCRIPTION
        "Cisco UCS sysdebug:AutoCoreFileExportTarget:name
        managed object property"
    ::= { cucsSysdebugAutoCoreFileExportTargetEntry 18 }

cucsSysdebugAutoCoreFileExportTargetPath OBJECT-TYPE
    SYNTAX       SnmpAdminString
    MAX-ACCESS   read-only
    STATUS       current
    DESCRIPTION
        "Cisco UCS sysdebug:AutoCoreFileExportTarget:path
        managed object property"
    ::= { cucsSysdebugAutoCoreFileExportTargetEntry 19 }

cucsSysdebugAutoCoreFileExportTargetPort OBJECT-TYPE
    SYNTAX       Gauge32
    MAX-ACCESS   read-only
    STATUS       current
    DESCRIPTION
        "Cisco UCS sysdebug:AutoCoreFileExportTarget:port
        managed object property"
    ::= { cucsSysdebugAutoCoreFileExportTargetEntry 20 }

cucsSysdebugAutoCoreFileExportTargetPostAction OBJECT-TYPE
    SYNTAX       CucsSysfileExporterPostAction
    MAX-ACCESS   read-only
    STATUS       current
    DESCRIPTION
        "Cisco UCS sysdebug:AutoCoreFileExportTarget:postAction
        managed object property"
    ::= { cucsSysdebugAutoCoreFileExportTargetEntry 21 }

cucsSysdebugAutoCoreFileExportTargetProto OBJECT-TYPE
    SYNTAX       CucsSysdebugAutoCoreFileExportTargetProto
    MAX-ACCESS   read-only
    STATUS       current
    DESCRIPTION
        "Cisco UCS sysdebug:AutoCoreFileExportTarget:proto
        managed object property"
    ::= { cucsSysdebugAutoCoreFileExportTargetEntry 22 }

cucsSysdebugAutoCoreFileExportTargetExportFailureReason OBJECT-TYPE
    SYNTAX       SnmpAdminString
    MAX-ACCESS   read-only
    STATUS       current
    DESCRIPTION
        "Cisco UCS sysdebug:AutoCoreFileExportTarget:exportFailureReason
        managed object property"
    ::= { cucsSysdebugAutoCoreFileExportTargetEntry 23 }

cucsSysdebugAutoCoreFileExportTargetExportStatus OBJECT-TYPE
    SYNTAX       CucsSysdebugCoreExportStatus
    MAX-ACCESS   read-only
    STATUS       current
    DESCRIPTION
        "Cisco UCS sysdebug:AutoCoreFileExportTarget:exportStatus
        managed object property"
    ::= { cucsSysdebugAutoCoreFileExportTargetEntry 24 }

cucsSysdebugAutoCoreFileExportTargetFsmTaskTable OBJECT-TYPE
    SYNTAX           SEQUENCE OF CucsSysdebugAutoCoreFileExportTargetFsmTaskEntry
    MAX-ACCESS       not-accessible
    STATUS           current
    DESCRIPTION
        "Cisco UCS sysdebug:AutoCoreFileExportTargetFsmTask
        managed object table"
    ::= { cucsSysdebugObjects 2 }

cucsSysdebugAutoCoreFileExportTargetFsmTaskEntry OBJECT-TYPE
    SYNTAX           CucsSysdebugAutoCoreFileExportTargetFsmTaskEntry
    MAX-ACCESS       not-accessible
    STATUS           current
    DESCRIPTION
        "Entry for the cucsSysdebugAutoCoreFileExportTargetFsmTaskTable table."
    INDEX { cucsSysdebugAutoCoreFileExportTargetFsmTaskInstanceId }
    ::= { cucsSysdebugAutoCoreFileExportTargetFsmTaskTable 1 }

CucsSysdebugAutoCoreFileExportTargetFsmTaskEntry ::= SEQUENCE {
    cucsSysdebugAutoCoreFileExportTargetFsmTaskInstanceId            CucsManagedObjectId,
    cucsSysdebugAutoCoreFileExportTargetFsmTaskDn                    CucsManagedObjectDn,
    cucsSysdebugAutoCoreFileExportTargetFsmTaskRn                    SnmpAdminString,
    cucsSysdebugAutoCoreFileExportTargetFsmTaskCompletion            CucsFsmCompletion,
    cucsSysdebugAutoCoreFileExportTargetFsmTaskFlags                 CucsFsmFlags,
    cucsSysdebugAutoCoreFileExportTargetFsmTaskItem                  CucsSysdebugAutoCoreFileExportTargetFsmTaskItem,
    cucsSysdebugAutoCoreFileExportTargetFsmTaskSeqId                 Gauge32
}

cucsSysdebugAutoCoreFileExportTargetFsmTaskInstanceId OBJECT-TYPE
    SYNTAX       CucsManagedObjectId
    MAX-ACCESS   not-accessible
    STATUS       current
    DESCRIPTION
        "Instance identifier of the managed object."
    ::= { cucsSysdebugAutoCoreFileExportTargetFsmTaskEntry 1 }

cucsSysdebugAutoCoreFileExportTargetFsmTaskDn OBJECT-TYPE
    SYNTAX       CucsManagedObjectDn
    MAX-ACCESS   read-only
    STATUS       current
    DESCRIPTION
        "Cisco UCS sysdebug:AutoCoreFileExportTargetFsmTask:dn
        managed object property"
    ::= { cucsSysdebugAutoCoreFileExportTargetFsmTaskEntry 2 }

cucsSysdebugAutoCoreFileExportTargetFsmTaskRn OBJECT-TYPE
    SYNTAX       SnmpAdminString
    MAX-ACCESS   read-only
    STATUS       current
    DESCRIPTION
        "Cisco UCS sysdebug:AutoCoreFileExportTargetFsmTask:rn
        managed object property"
    ::= { cucsSysdebugAutoCoreFileExportTargetFsmTaskEntry 3 }

cucsSysdebugAutoCoreFileExportTargetFsmTaskCompletion OBJECT-TYPE
    SYNTAX       CucsFsmCompletion
    MAX-ACCESS   read-only
    STATUS       current
    DESCRIPTION
        "Cisco UCS sysdebug:AutoCoreFileExportTargetFsmTask:completion
        managed object property"
    ::= { cucsSysdebugAutoCoreFileExportTargetFsmTaskEntry 4 }

cucsSysdebugAutoCoreFileExportTargetFsmTaskFlags OBJECT-TYPE
    SYNTAX       CucsFsmFlags
    MAX-ACCESS   read-only
    STATUS       current
    DESCRIPTION
        "Cisco UCS sysdebug:AutoCoreFileExportTargetFsmTask:flags
        managed object property"
    ::= { cucsSysdebugAutoCoreFileExportTargetFsmTaskEntry 5 }

cucsSysdebugAutoCoreFileExportTargetFsmTaskItem OBJECT-TYPE
    SYNTAX       CucsSysdebugAutoCoreFileExportTargetFsmTaskItem
    MAX-ACCESS   read-only
    STATUS       current
    DESCRIPTION
        "Cisco UCS sysdebug:AutoCoreFileExportTargetFsmTask:item
        managed object property"
    ::= { cucsSysdebugAutoCoreFileExportTargetFsmTaskEntry 6 }

cucsSysdebugAutoCoreFileExportTargetFsmTaskSeqId OBJECT-TYPE
    SYNTAX       Gauge32
    MAX-ACCESS   read-only
    STATUS       current
    DESCRIPTION
        "Cisco UCS sysdebug:AutoCoreFileExportTargetFsmTask:seqId
        managed object property"
    ::= { cucsSysdebugAutoCoreFileExportTargetFsmTaskEntry 7 }

cucsSysdebugBackupBehaviorTable OBJECT-TYPE
    SYNTAX           SEQUENCE OF CucsSysdebugBackupBehaviorEntry
    MAX-ACCESS       not-accessible
    STATUS           current
    DESCRIPTION
        "Cisco UCS sysdebug:BackupBehavior managed object table"
    ::= { cucsSysdebugObjects 3 }

cucsSysdebugBackupBehaviorEntry OBJECT-TYPE
    SYNTAX           CucsSysdebugBackupBehaviorEntry
    MAX-ACCESS       not-accessible
    STATUS           current
    DESCRIPTION
        "Entry for the cucsSysdebugBackupBehaviorTable table."
    INDEX { cucsSysdebugBackupBehaviorInstanceId }
    ::= { cucsSysdebugBackupBehaviorTable 1 }

CucsSysdebugBackupBehaviorEntry ::= SEQUENCE {
    cucsSysdebugBackupBehaviorInstanceId                             CucsManagedObjectId,
    cucsSysdebugBackupBehaviorDn                                     CucsManagedObjectDn,
    cucsSysdebugBackupBehaviorRn                                     SnmpAdminString,
    cucsSysdebugBackupBehaviorAction                                 CucsSysdebugEpLogBackupAction,
    cucsSysdebugBackupBehaviorClearOnBackup                          TruthValue,
    cucsSysdebugBackupBehaviorFormat                                 CucsSysdebugBackupFormat,
    cucsSysdebugBackupBehaviorHostname                               SnmpAdminString,
    cucsSysdebugBackupBehaviorInterval                               CucsSysdebugBackupBehaviorInterval,
    cucsSysdebugBackupBehaviorProto                                  CucsSysdebugBackupBehaviorProto,
    cucsSysdebugBackupBehaviorPwd                                    SnmpAdminString,
    cucsSysdebugBackupBehaviorRemotePath                             SnmpAdminString,
    cucsSysdebugBackupBehaviorUser                                   SnmpAdminString
}

cucsSysdebugBackupBehaviorInstanceId OBJECT-TYPE
    SYNTAX       CucsManagedObjectId
    MAX-ACCESS   not-accessible
    STATUS       current
    DESCRIPTION
        "Instance identifier of the managed object."
    ::= { cucsSysdebugBackupBehaviorEntry 1 }

cucsSysdebugBackupBehaviorDn OBJECT-TYPE
    SYNTAX       CucsManagedObjectDn
    MAX-ACCESS   read-only
    STATUS       current
    DESCRIPTION
        "Cisco UCS sysdebug:BackupBehavior:dn managed object property"
    ::= { cucsSysdebugBackupBehaviorEntry 2 }

cucsSysdebugBackupBehaviorRn OBJECT-TYPE
    SYNTAX       SnmpAdminString
    MAX-ACCESS   read-only
    STATUS       current
    DESCRIPTION
        "Cisco UCS sysdebug:BackupBehavior:rn managed object property"
    ::= { cucsSysdebugBackupBehaviorEntry 3 }

cucsSysdebugBackupBehaviorAction OBJECT-TYPE
    SYNTAX       CucsSysdebugEpLogBackupAction
    MAX-ACCESS   read-only
    STATUS       current
    DESCRIPTION
        "Cisco UCS sysdebug:BackupBehavior:action managed object property"
    ::= { cucsSysdebugBackupBehaviorEntry 4 }

cucsSysdebugBackupBehaviorClearOnBackup OBJECT-TYPE
    SYNTAX       TruthValue
    MAX-ACCESS   read-only
    STATUS       current
    DESCRIPTION
        "Cisco UCS sysdebug:BackupBehavior:clearOnBackup
        managed object property"
    ::= { cucsSysdebugBackupBehaviorEntry 5 }

cucsSysdebugBackupBehaviorFormat OBJECT-TYPE
    SYNTAX       CucsSysdebugBackupFormat
    MAX-ACCESS   read-only
    STATUS       current
    DESCRIPTION
        "Cisco UCS sysdebug:BackupBehavior:format managed object property"
    ::= { cucsSysdebugBackupBehaviorEntry 6 }

cucsSysdebugBackupBehaviorHostname OBJECT-TYPE
    SYNTAX       SnmpAdminString
    MAX-ACCESS   read-only
    STATUS       current
    DESCRIPTION
        "Cisco UCS sysdebug:BackupBehavior:hostname managed
        object property"
    ::= { cucsSysdebugBackupBehaviorEntry 7 }

cucsSysdebugBackupBehaviorInterval OBJECT-TYPE
    SYNTAX       CucsSysdebugBackupBehaviorInterval
    MAX-ACCESS   read-only
    STATUS       current
    DESCRIPTION
        "Cisco UCS sysdebug:BackupBehavior:interval managed
        object property"
    ::= { cucsSysdebugBackupBehaviorEntry 8 }

cucsSysdebugBackupBehaviorProto OBJECT-TYPE
    SYNTAX       CucsSysdebugBackupBehaviorProto
    MAX-ACCESS   read-only
    STATUS       current
    DESCRIPTION
        "Cisco UCS sysdebug:BackupBehavior:proto managed object property"
    ::= { cucsSysdebugBackupBehaviorEntry 9 }

cucsSysdebugBackupBehaviorPwd OBJECT-TYPE
    SYNTAX       SnmpAdminString
    MAX-ACCESS   read-only
    STATUS       current
    DESCRIPTION
        "Cisco UCS sysdebug:BackupBehavior:pwd managed object property"
    ::= { cucsSysdebugBackupBehaviorEntry 10 }

cucsSysdebugBackupBehaviorRemotePath OBJECT-TYPE
    SYNTAX       SnmpAdminString
    MAX-ACCESS   read-only
    STATUS       current
    DESCRIPTION
        "Cisco UCS sysdebug:BackupBehavior:remotePath managed
        object property"
    ::= { cucsSysdebugBackupBehaviorEntry 11 }

cucsSysdebugBackupBehaviorUser OBJECT-TYPE
    SYNTAX       SnmpAdminString
    MAX-ACCESS   read-only
    STATUS       current
    DESCRIPTION
        "Cisco UCS sysdebug:BackupBehavior:user managed object property"
    ::= { cucsSysdebugBackupBehaviorEntry 12 }

cucsSysdebugCoreTable OBJECT-TYPE
    SYNTAX           SEQUENCE OF CucsSysdebugCoreEntry
    MAX-ACCESS       not-accessible
    STATUS           current
    DESCRIPTION
        "Cisco UCS sysdebug:Core managed object table"
    ::= { cucsSysdebugObjects 4 }

cucsSysdebugCoreEntry OBJECT-TYPE
    SYNTAX           CucsSysdebugCoreEntry
    MAX-ACCESS       not-accessible
    STATUS           current
    DESCRIPTION
        "Entry for the cucsSysdebugCoreTable table."
    INDEX { cucsSysdebugCoreInstanceId }
    ::= { cucsSysdebugCoreTable 1 }

CucsSysdebugCoreEntry ::= SEQUENCE {
    cucsSysdebugCoreInstanceId                                       CucsManagedObjectId,
    cucsSysdebugCoreDn                                               CucsManagedObjectDn,
    cucsSysdebugCoreRn                                               SnmpAdminString,
    cucsSysdebugCoreDescr                                            SnmpAdminString,
    cucsSysdebugCoreName                                             SnmpAdminString,
    cucsSysdebugCoreSize                                             Gauge32,
    cucsSysdebugCoreSwitchId                                         CucsNetworkSwitchId,
    cucsSysdebugCoreTs                                               DateAndTime,
    cucsSysdebugCoreUri                                              SnmpAdminString,
    cucsSysdebugCoreAdminState                                       CucsSysdebugCoreFileAdminState,
    cucsSysdebugCoreFsmDescr                                         SnmpAdminString,
    cucsSysdebugCoreFsmPrev                                          SnmpAdminString,
    cucsSysdebugCoreFsmProgr                                         Gauge32,
    cucsSysdebugCoreFsmRmtInvErrCode                                 Gauge32,
    cucsSysdebugCoreFsmRmtInvErrDescr                                SnmpAdminString,
    cucsSysdebugCoreFsmRmtInvRslt                                    CucsConditionRemoteInvRslt,
    cucsSysdebugCoreFsmStageDescr                                    SnmpAdminString,
    cucsSysdebugCoreFsmStamp                                         DateAndTime,
    cucsSysdebugCoreFsmStatus                                        SnmpAdminString,
    cucsSysdebugCoreFsmTry                                           Gauge32,
    cucsSysdebugCoreOperState                                        CucsSysdebugCoreFileOperState
}

cucsSysdebugCoreInstanceId OBJECT-TYPE
    SYNTAX       CucsManagedObjectId
    MAX-ACCESS   not-accessible
    STATUS       current
    DESCRIPTION
        "Instance identifier of the managed object."
    ::= { cucsSysdebugCoreEntry 1 }

cucsSysdebugCoreDn OBJECT-TYPE
    SYNTAX       CucsManagedObjectDn
    MAX-ACCESS   read-only
    STATUS       current
    DESCRIPTION
        "Cisco UCS sysdebug:Core:dn managed object property"
    ::= { cucsSysdebugCoreEntry 2 }

cucsSysdebugCoreRn OBJECT-TYPE
    SYNTAX       SnmpAdminString
    MAX-ACCESS   read-only
    STATUS       current
    DESCRIPTION
        "Cisco UCS sysdebug:Core:rn managed object property"
    ::= { cucsSysdebugCoreEntry 3 }

cucsSysdebugCoreDescr OBJECT-TYPE
    SYNTAX       SnmpAdminString
    MAX-ACCESS   read-only
    STATUS       current
    DESCRIPTION
        "Cisco UCS sysdebug:Core:descr managed object property"
    ::= { cucsSysdebugCoreEntry 4 }

cucsSysdebugCoreName OBJECT-TYPE
    SYNTAX       SnmpAdminString
    MAX-ACCESS   read-only
    STATUS       current
    DESCRIPTION
        "Cisco UCS sysdebug:Core:name managed object property"
    ::= { cucsSysdebugCoreEntry 5 }

cucsSysdebugCoreSize OBJECT-TYPE
    SYNTAX       Gauge32
    MAX-ACCESS   read-only
    STATUS       current
    DESCRIPTION
        "Cisco UCS sysdebug:Core:size managed object property"
    ::= { cucsSysdebugCoreEntry 6 }

cucsSysdebugCoreSwitchId OBJECT-TYPE
    SYNTAX       CucsNetworkSwitchId
    MAX-ACCESS   read-only
    STATUS       current
    DESCRIPTION
        "Cisco UCS sysdebug:Core:switchId managed object property"
    ::= { cucsSysdebugCoreEntry 7 }

cucsSysdebugCoreTs OBJECT-TYPE
    SYNTAX       DateAndTime
    MAX-ACCESS   read-only
    STATUS       current
    DESCRIPTION
        "Cisco UCS sysdebug:Core:ts managed object property"
    ::= { cucsSysdebugCoreEntry 8 }

cucsSysdebugCoreUri OBJECT-TYPE
    SYNTAX       SnmpAdminString
    MAX-ACCESS   read-only
    STATUS       current
    DESCRIPTION
        "Cisco UCS sysdebug:Core:uri managed object property"
    ::= { cucsSysdebugCoreEntry 9 }

cucsSysdebugCoreAdminState OBJECT-TYPE
    SYNTAX       CucsSysdebugCoreFileAdminState
    MAX-ACCESS   read-only
    STATUS       current
    DESCRIPTION
        "Cisco UCS sysdebug:Core:adminState managed object property"
    ::= { cucsSysdebugCoreEntry 10 }

cucsSysdebugCoreFsmDescr OBJECT-TYPE
    SYNTAX       SnmpAdminString
    MAX-ACCESS   read-only
    STATUS       current
    DESCRIPTION
        "Cisco UCS sysdebug:Core:fsmDescr managed object property"
    ::= { cucsSysdebugCoreEntry 11 }

cucsSysdebugCoreFsmPrev OBJECT-TYPE
    SYNTAX       SnmpAdminString
    MAX-ACCESS   read-only
    STATUS       current
    DESCRIPTION
        "Cisco UCS sysdebug:Core:fsmPrev managed object property"
    ::= { cucsSysdebugCoreEntry 12 }

cucsSysdebugCoreFsmProgr OBJECT-TYPE
    SYNTAX       Gauge32
    MAX-ACCESS   read-only
    STATUS       current
    DESCRIPTION
        "Cisco UCS sysdebug:Core:fsmProgr managed object property"
    ::= { cucsSysdebugCoreEntry 13 }

cucsSysdebugCoreFsmRmtInvErrCode OBJECT-TYPE
    SYNTAX       Gauge32
    MAX-ACCESS   read-only
    STATUS       current
    DESCRIPTION
        "Cisco UCS sysdebug:Core:fsmRmtInvErrCode managed object property"
    ::= { cucsSysdebugCoreEntry 14 }

cucsSysdebugCoreFsmRmtInvErrDescr OBJECT-TYPE
    SYNTAX       SnmpAdminString
    MAX-ACCESS   read-only
    STATUS       current
    DESCRIPTION
        "Cisco UCS sysdebug:Core:fsmRmtInvErrDescr managed
        object property"
    ::= { cucsSysdebugCoreEntry 15 }

cucsSysdebugCoreFsmRmtInvRslt OBJECT-TYPE
    SYNTAX       CucsConditionRemoteInvRslt
    MAX-ACCESS   read-only
    STATUS       current
    DESCRIPTION
        "Cisco UCS sysdebug:Core:fsmRmtInvRslt managed object property"
    ::= { cucsSysdebugCoreEntry 16 }

cucsSysdebugCoreFsmStageDescr OBJECT-TYPE
    SYNTAX       SnmpAdminString
    MAX-ACCESS   read-only
    STATUS       current
    DESCRIPTION
        "Cisco UCS sysdebug:Core:fsmStageDescr managed object property"
    ::= { cucsSysdebugCoreEntry 17 }

cucsSysdebugCoreFsmStamp OBJECT-TYPE
    SYNTAX       DateAndTime
    MAX-ACCESS   read-only
    STATUS       current
    DESCRIPTION
        "Cisco UCS sysdebug:Core:fsmStamp managed object property"
    ::= { cucsSysdebugCoreEntry 18 }

cucsSysdebugCoreFsmStatus OBJECT-TYPE
    SYNTAX       SnmpAdminString
    MAX-ACCESS   read-only
    STATUS       current
    DESCRIPTION
        "Cisco UCS sysdebug:Core:fsmStatus managed object property"
    ::= { cucsSysdebugCoreEntry 19 }

cucsSysdebugCoreFsmTry OBJECT-TYPE
    SYNTAX       Gauge32
    MAX-ACCESS   read-only
    STATUS       current
    DESCRIPTION
        "Cisco UCS sysdebug:Core:fsmTry managed object property"
    ::= { cucsSysdebugCoreEntry 20 }

cucsSysdebugCoreOperState OBJECT-TYPE
    SYNTAX       CucsSysdebugCoreFileOperState
    MAX-ACCESS   read-only
    STATUS       current
    DESCRIPTION
        "Cisco UCS sysdebug:Core:operState managed object property"
    ::= { cucsSysdebugCoreEntry 21 }

cucsSysdebugCoreFileRepositoryTable OBJECT-TYPE
    SYNTAX           SEQUENCE OF CucsSysdebugCoreFileRepositoryEntry
    MAX-ACCESS       not-accessible
    STATUS           current
    DESCRIPTION
        "Cisco UCS sysdebug:CoreFileRepository managed object table"
    ::= { cucsSysdebugObjects 5 }

cucsSysdebugCoreFileRepositoryEntry OBJECT-TYPE
    SYNTAX           CucsSysdebugCoreFileRepositoryEntry
    MAX-ACCESS       not-accessible
    STATUS           current
    DESCRIPTION
        "Entry for the cucsSysdebugCoreFileRepositoryTable table."
    INDEX { cucsSysdebugCoreFileRepositoryInstanceId }
    ::= { cucsSysdebugCoreFileRepositoryTable 1 }

CucsSysdebugCoreFileRepositoryEntry ::= SEQUENCE {
    cucsSysdebugCoreFileRepositoryInstanceId                         CucsManagedObjectId,
    cucsSysdebugCoreFileRepositoryDn                                 CucsManagedObjectDn,
    cucsSysdebugCoreFileRepositoryRn                                 SnmpAdminString
}

cucsSysdebugCoreFileRepositoryInstanceId OBJECT-TYPE
    SYNTAX       CucsManagedObjectId
    MAX-ACCESS   not-accessible
    STATUS       current
    DESCRIPTION
        "Instance identifier of the managed object."
    ::= { cucsSysdebugCoreFileRepositoryEntry 1 }

cucsSysdebugCoreFileRepositoryDn OBJECT-TYPE
    SYNTAX       CucsManagedObjectDn
    MAX-ACCESS   read-only
    STATUS       current
    DESCRIPTION
        "Cisco UCS sysdebug:CoreFileRepository:dn managed object property"
    ::= { cucsSysdebugCoreFileRepositoryEntry 2 }

cucsSysdebugCoreFileRepositoryRn OBJECT-TYPE
    SYNTAX       SnmpAdminString
    MAX-ACCESS   read-only
    STATUS       current
    DESCRIPTION
        "Cisco UCS sysdebug:CoreFileRepository:rn managed object property"
    ::= { cucsSysdebugCoreFileRepositoryEntry 3 }

cucsSysdebugCoreFsmTaskTable OBJECT-TYPE
    SYNTAX           SEQUENCE OF CucsSysdebugCoreFsmTaskEntry
    MAX-ACCESS       not-accessible
    STATUS           current
    DESCRIPTION
        "Cisco UCS sysdebug:CoreFsmTask managed object table"
    ::= { cucsSysdebugObjects 21 }

cucsSysdebugCoreFsmTaskEntry OBJECT-TYPE
    SYNTAX           CucsSysdebugCoreFsmTaskEntry
    MAX-ACCESS       not-accessible
    STATUS           current
    DESCRIPTION
        "Entry for the cucsSysdebugCoreFsmTaskTable table."
    INDEX { cucsSysdebugCoreFsmTaskInstanceId }
    ::= { cucsSysdebugCoreFsmTaskTable 1 }

CucsSysdebugCoreFsmTaskEntry ::= SEQUENCE {
    cucsSysdebugCoreFsmTaskInstanceId                                CucsManagedObjectId,
    cucsSysdebugCoreFsmTaskDn                                        CucsManagedObjectDn,
    cucsSysdebugCoreFsmTaskRn                                        SnmpAdminString,
    cucsSysdebugCoreFsmTaskCompletion                                CucsFsmCompletion,
    cucsSysdebugCoreFsmTaskFlags                                     CucsFsmFlags,
    cucsSysdebugCoreFsmTaskItem                                      CucsSysdebugCoreFsmTaskItem,
    cucsSysdebugCoreFsmTaskSeqId                                     Gauge32
}

cucsSysdebugCoreFsmTaskInstanceId OBJECT-TYPE
    SYNTAX       CucsManagedObjectId
    MAX-ACCESS   not-accessible
    STATUS       current
    DESCRIPTION
        "Instance identifier of the managed object."
    ::= { cucsSysdebugCoreFsmTaskEntry 1 }

cucsSysdebugCoreFsmTaskDn OBJECT-TYPE
    SYNTAX       CucsManagedObjectDn
    MAX-ACCESS   read-only
    STATUS       current
    DESCRIPTION
        "Cisco UCS sysdebug:CoreFsmTask:dn managed object property"
    ::= { cucsSysdebugCoreFsmTaskEntry 2 }

cucsSysdebugCoreFsmTaskRn OBJECT-TYPE
    SYNTAX       SnmpAdminString
    MAX-ACCESS   read-only
    STATUS       current
    DESCRIPTION
        "Cisco UCS sysdebug:CoreFsmTask:rn managed object property"
    ::= { cucsSysdebugCoreFsmTaskEntry 3 }

cucsSysdebugCoreFsmTaskCompletion OBJECT-TYPE
    SYNTAX       CucsFsmCompletion
    MAX-ACCESS   read-only
    STATUS       current
    DESCRIPTION
        "Cisco UCS sysdebug:CoreFsmTask:completion managed
        object property"
    ::= { cucsSysdebugCoreFsmTaskEntry 4 }

cucsSysdebugCoreFsmTaskFlags OBJECT-TYPE
    SYNTAX       CucsFsmFlags
    MAX-ACCESS   read-only
    STATUS       current
    DESCRIPTION
        "Cisco UCS sysdebug:CoreFsmTask:flags managed object property"
    ::= { cucsSysdebugCoreFsmTaskEntry 5 }

cucsSysdebugCoreFsmTaskItem OBJECT-TYPE
    SYNTAX       CucsSysdebugCoreFsmTaskItem
    MAX-ACCESS   read-only
    STATUS       current
    DESCRIPTION
        "Cisco UCS sysdebug:CoreFsmTask:item managed object property"
    ::= { cucsSysdebugCoreFsmTaskEntry 6 }

cucsSysdebugCoreFsmTaskSeqId OBJECT-TYPE
    SYNTAX       Gauge32
    MAX-ACCESS   read-only
    STATUS       current
    DESCRIPTION
        "Cisco UCS sysdebug:CoreFsmTask:seqId managed object property"
    ::= { cucsSysdebugCoreFsmTaskEntry 7 }

cucsSysdebugEpTable OBJECT-TYPE
    SYNTAX           SEQUENCE OF CucsSysdebugEpEntry
    MAX-ACCESS       not-accessible
    STATUS           current
    DESCRIPTION
        "Cisco UCS sysdebug:Ep managed object table"
    ::= { cucsSysdebugObjects 6 }

cucsSysdebugEpEntry OBJECT-TYPE
    SYNTAX           CucsSysdebugEpEntry
    MAX-ACCESS       not-accessible
    STATUS           current
    DESCRIPTION
        "Entry for the cucsSysdebugEpTable table."
    INDEX { cucsSysdebugEpInstanceId }
    ::= { cucsSysdebugEpTable 1 }

CucsSysdebugEpEntry ::= SEQUENCE {
    cucsSysdebugEpInstanceId                                         CucsManagedObjectId,
    cucsSysdebugEpDn                                                 CucsManagedObjectDn,
    cucsSysdebugEpRn                                                 SnmpAdminString
}

cucsSysdebugEpInstanceId OBJECT-TYPE
    SYNTAX       CucsManagedObjectId
    MAX-ACCESS   not-accessible
    STATUS       current
    DESCRIPTION
        "Instance identifier of the managed object."
    ::= { cucsSysdebugEpEntry 1 }

cucsSysdebugEpDn OBJECT-TYPE
    SYNTAX       CucsManagedObjectDn
    MAX-ACCESS   read-only
    STATUS       current
    DESCRIPTION
        "Cisco UCS sysdebug:Ep:dn managed object property"
    ::= { cucsSysdebugEpEntry 2 }

cucsSysdebugEpRn OBJECT-TYPE
    SYNTAX       SnmpAdminString
    MAX-ACCESS   read-only
    STATUS       current
    DESCRIPTION
        "Cisco UCS sysdebug:Ep:rn managed object property"
    ::= { cucsSysdebugEpEntry 3 }

cucsSysdebugLogControlDestinationFileTable OBJECT-TYPE
    SYNTAX           SEQUENCE OF CucsSysdebugLogControlDestinationFileEntry
    MAX-ACCESS       not-accessible
    STATUS           current
    DESCRIPTION
        "Cisco UCS sysdebug:LogControlDestinationFile managed
        object table"
    ::= { cucsSysdebugObjects 7 }

cucsSysdebugLogControlDestinationFileEntry OBJECT-TYPE
    SYNTAX           CucsSysdebugLogControlDestinationFileEntry
    MAX-ACCESS       not-accessible
    STATUS           current
    DESCRIPTION
        "Entry for the cucsSysdebugLogControlDestinationFileTable table."
    INDEX { cucsSysdebugLogControlDestinationFileInstanceId }
    ::= { cucsSysdebugLogControlDestinationFileTable 1 }

CucsSysdebugLogControlDestinationFileEntry ::= SEQUENCE {
    cucsSysdebugLogControlDestinationFileInstanceId                  CucsManagedObjectId,
    cucsSysdebugLogControlDestinationFileDn                          CucsManagedObjectDn,
    cucsSysdebugLogControlDestinationFileRn                          SnmpAdminString,
    cucsSysdebugLogControlDestinationFileBackupCount                 Gauge32,
    cucsSysdebugLogControlDestinationFileDefaultLevel                CucsSysdebugLogControlLevel,
    cucsSysdebugLogControlDestinationFileDefaultSize                 Gauge32,
    cucsSysdebugLogControlDestinationFileLevel                       CucsSysdebugLogControlLevel,
    cucsSysdebugLogControlDestinationFileSize                        Gauge32
}

cucsSysdebugLogControlDestinationFileInstanceId OBJECT-TYPE
    SYNTAX       CucsManagedObjectId
    MAX-ACCESS   not-accessible
    STATUS       current
    DESCRIPTION
        "Instance identifier of the managed object."
    ::= { cucsSysdebugLogControlDestinationFileEntry 1 }

cucsSysdebugLogControlDestinationFileDn OBJECT-TYPE
    SYNTAX       CucsManagedObjectDn
    MAX-ACCESS   read-only
    STATUS       current
    DESCRIPTION
        "Cisco UCS sysdebug:LogControlDestinationFile:dn
        managed object property"
    ::= { cucsSysdebugLogControlDestinationFileEntry 2 }

cucsSysdebugLogControlDestinationFileRn OBJECT-TYPE
    SYNTAX       SnmpAdminString
    MAX-ACCESS   read-only
    STATUS       current
    DESCRIPTION
        "Cisco UCS sysdebug:LogControlDestinationFile:rn
        managed object property"
    ::= { cucsSysdebugLogControlDestinationFileEntry 3 }

cucsSysdebugLogControlDestinationFileBackupCount OBJECT-TYPE
    SYNTAX       Gauge32
    MAX-ACCESS   read-only
    STATUS       current
    DESCRIPTION
        "Cisco UCS sysdebug:LogControlDestinationFile:backupCount
        managed object property"
    ::= { cucsSysdebugLogControlDestinationFileEntry 4 }

cucsSysdebugLogControlDestinationFileDefaultLevel OBJECT-TYPE
    SYNTAX       CucsSysdebugLogControlLevel
    MAX-ACCESS   read-only
    STATUS       current
    DESCRIPTION
        "Cisco UCS sysdebug:LogControlDestinationFile:defaultLevel
        managed object property"
    ::= { cucsSysdebugLogControlDestinationFileEntry 5 }

cucsSysdebugLogControlDestinationFileDefaultSize OBJECT-TYPE
    SYNTAX       Gauge32
    MAX-ACCESS   read-only
    STATUS       current
    DESCRIPTION
        "Cisco UCS sysdebug:LogControlDestinationFile:defaultSize
        managed object property"
    ::= { cucsSysdebugLogControlDestinationFileEntry 6 }

cucsSysdebugLogControlDestinationFileLevel OBJECT-TYPE
    SYNTAX       CucsSysdebugLogControlLevel
    MAX-ACCESS   read-only
    STATUS       current
    DESCRIPTION
        "Cisco UCS sysdebug:LogControlDestinationFile:level
        managed object property"
    ::= { cucsSysdebugLogControlDestinationFileEntry 7 }

cucsSysdebugLogControlDestinationFileSize OBJECT-TYPE
    SYNTAX       Gauge32
    MAX-ACCESS   read-only
    STATUS       current
    DESCRIPTION
        "Cisco UCS sysdebug:LogControlDestinationFile:size
        managed object property"
    ::= { cucsSysdebugLogControlDestinationFileEntry 8 }

cucsSysdebugLogControlDestinationSyslogTable OBJECT-TYPE
    SYNTAX           SEQUENCE OF CucsSysdebugLogControlDestinationSyslogEntry
    MAX-ACCESS       not-accessible
    STATUS           current
    DESCRIPTION
        "Cisco UCS sysdebug:LogControlDestinationSyslog
        managed object table"
    ::= { cucsSysdebugObjects 8 }

cucsSysdebugLogControlDestinationSyslogEntry OBJECT-TYPE
    SYNTAX           CucsSysdebugLogControlDestinationSyslogEntry
    MAX-ACCESS       not-accessible
    STATUS           current
    DESCRIPTION
        "Entry for the cucsSysdebugLogControlDestinationSyslogTable table."
    INDEX { cucsSysdebugLogControlDestinationSyslogInstanceId }
    ::= { cucsSysdebugLogControlDestinationSyslogTable 1 }

CucsSysdebugLogControlDestinationSyslogEntry ::= SEQUENCE {
    cucsSysdebugLogControlDestinationSyslogInstanceId                CucsManagedObjectId,
    cucsSysdebugLogControlDestinationSyslogDn                        CucsManagedObjectDn,
    cucsSysdebugLogControlDestinationSyslogRn                        SnmpAdminString,
    cucsSysdebugLogControlDestinationSyslogDefaultLevel              CucsSysdebugLogControlLevel,
    cucsSysdebugLogControlDestinationSyslogLevel                     CucsSysdebugLogControlLevel
}

cucsSysdebugLogControlDestinationSyslogInstanceId OBJECT-TYPE
    SYNTAX       CucsManagedObjectId
    MAX-ACCESS   not-accessible
    STATUS       current
    DESCRIPTION
        "Instance identifier of the managed object."
    ::= { cucsSysdebugLogControlDestinationSyslogEntry 1 }

cucsSysdebugLogControlDestinationSyslogDn OBJECT-TYPE
    SYNTAX       CucsManagedObjectDn
    MAX-ACCESS   read-only
    STATUS       current
    DESCRIPTION
        "Cisco UCS sysdebug:LogControlDestinationSyslog:dn
        managed object property"
    ::= { cucsSysdebugLogControlDestinationSyslogEntry 2 }

cucsSysdebugLogControlDestinationSyslogRn OBJECT-TYPE
    SYNTAX       SnmpAdminString
    MAX-ACCESS   read-only
    STATUS       current
    DESCRIPTION
        "Cisco UCS sysdebug:LogControlDestinationSyslog:rn
        managed object property"
    ::= { cucsSysdebugLogControlDestinationSyslogEntry 3 }

cucsSysdebugLogControlDestinationSyslogDefaultLevel OBJECT-TYPE
    SYNTAX       CucsSysdebugLogControlLevel
    MAX-ACCESS   read-only
    STATUS       current
    DESCRIPTION
        "Cisco UCS sysdebug:LogControlDestinationSyslog:defaultLevel
        managed object property"
    ::= { cucsSysdebugLogControlDestinationSyslogEntry 4 }

cucsSysdebugLogControlDestinationSyslogLevel OBJECT-TYPE
    SYNTAX       CucsSysdebugLogControlLevel
    MAX-ACCESS   read-only
    STATUS       current
    DESCRIPTION
        "Cisco UCS sysdebug:LogControlDestinationSyslog:level
        managed object property"
    ::= { cucsSysdebugLogControlDestinationSyslogEntry 5 }

cucsSysdebugLogControlDomainTable OBJECT-TYPE
    SYNTAX           SEQUENCE OF CucsSysdebugLogControlDomainEntry
    MAX-ACCESS       not-accessible
    STATUS           current
    DESCRIPTION
        "Cisco UCS sysdebug:LogControlDomain managed object table"
    ::= { cucsSysdebugObjects 9 }

cucsSysdebugLogControlDomainEntry OBJECT-TYPE
    SYNTAX           CucsSysdebugLogControlDomainEntry
    MAX-ACCESS       not-accessible
    STATUS           current
    DESCRIPTION
        "Entry for the cucsSysdebugLogControlDomainTable table."
    INDEX { cucsSysdebugLogControlDomainInstanceId }
    ::= { cucsSysdebugLogControlDomainTable 1 }

CucsSysdebugLogControlDomainEntry ::= SEQUENCE {
    cucsSysdebugLogControlDomainInstanceId                           CucsManagedObjectId,
    cucsSysdebugLogControlDomainDn                                   CucsManagedObjectDn,
    cucsSysdebugLogControlDomainRn                                   SnmpAdminString,
    cucsSysdebugLogControlDomainLevel                                CucsSysdebugLogControlLevel,
    cucsSysdebugLogControlDomainLevelFlag                            TruthValue,
    cucsSysdebugLogControlDomainName                                 CucsSysdebugLogControlDomainEnum,
    cucsSysdebugLogControlDomainPersist                              TruthValue,
    cucsSysdebugLogControlDomainReset                                TruthValue
}

cucsSysdebugLogControlDomainInstanceId OBJECT-TYPE
    SYNTAX       CucsManagedObjectId
    MAX-ACCESS   not-accessible
    STATUS       current
    DESCRIPTION
        "Instance identifier of the managed object."
    ::= { cucsSysdebugLogControlDomainEntry 1 }

cucsSysdebugLogControlDomainDn OBJECT-TYPE
    SYNTAX       CucsManagedObjectDn
    MAX-ACCESS   read-only
    STATUS       current
    DESCRIPTION
        "Cisco UCS sysdebug:LogControlDomain:dn managed object property"
    ::= { cucsSysdebugLogControlDomainEntry 2 }

cucsSysdebugLogControlDomainRn OBJECT-TYPE
    SYNTAX       SnmpAdminString
    MAX-ACCESS   read-only
    STATUS       current
    DESCRIPTION
        "Cisco UCS sysdebug:LogControlDomain:rn managed object property"
    ::= { cucsSysdebugLogControlDomainEntry 3 }

cucsSysdebugLogControlDomainLevel OBJECT-TYPE
    SYNTAX       CucsSysdebugLogControlLevel
    MAX-ACCESS   read-only
    STATUS       current
    DESCRIPTION
        "Cisco UCS sysdebug:LogControlDomain:level managed
        object property"
    ::= { cucsSysdebugLogControlDomainEntry 4 }

cucsSysdebugLogControlDomainLevelFlag OBJECT-TYPE
    SYNTAX       TruthValue
    MAX-ACCESS   read-only
    STATUS       current
    DESCRIPTION
        "Cisco UCS sysdebug:LogControlDomain:levelFlag
        managed object property"
    ::= { cucsSysdebugLogControlDomainEntry 5 }

cucsSysdebugLogControlDomainName OBJECT-TYPE
    SYNTAX       CucsSysdebugLogControlDomainEnum
    MAX-ACCESS   read-only
    STATUS       current
    DESCRIPTION
        "Cisco UCS sysdebug:LogControlDomain:name managed object property"
    ::= { cucsSysdebugLogControlDomainEntry 6 }

cucsSysdebugLogControlDomainPersist OBJECT-TYPE
    SYNTAX       TruthValue
    MAX-ACCESS   read-only
    STATUS       current
    DESCRIPTION
        "Cisco UCS sysdebug:LogControlDomain:persist managed
        object property"
    ::= { cucsSysdebugLogControlDomainEntry 7 }

cucsSysdebugLogControlDomainReset OBJECT-TYPE
    SYNTAX       TruthValue
    MAX-ACCESS   read-only
    STATUS       current
    DESCRIPTION
        "Cisco UCS sysdebug:LogControlDomain:reset managed
        object property"
    ::= { cucsSysdebugLogControlDomainEntry 8 }

cucsSysdebugLogControlEpTable OBJECT-TYPE
    SYNTAX           SEQUENCE OF CucsSysdebugLogControlEpEntry
    MAX-ACCESS       not-accessible
    STATUS           current
    DESCRIPTION
        "Cisco UCS sysdebug:LogControlEp managed object table"
    ::= { cucsSysdebugObjects 10 }

cucsSysdebugLogControlEpEntry OBJECT-TYPE
    SYNTAX           CucsSysdebugLogControlEpEntry
    MAX-ACCESS       not-accessible
    STATUS           current
    DESCRIPTION
        "Entry for the cucsSysdebugLogControlEpTable table."
    INDEX { cucsSysdebugLogControlEpInstanceId }
    ::= { cucsSysdebugLogControlEpTable 1 }

CucsSysdebugLogControlEpEntry ::= SEQUENCE {
    cucsSysdebugLogControlEpInstanceId                               CucsManagedObjectId,
    cucsSysdebugLogControlEpDn                                       CucsManagedObjectDn,
    cucsSysdebugLogControlEpRn                                       SnmpAdminString,
    cucsSysdebugLogControlEpFsmDescr                                 SnmpAdminString,
    cucsSysdebugLogControlEpFsmPrev                                  SnmpAdminString,
    cucsSysdebugLogControlEpFsmProgr                                 Gauge32,
    cucsSysdebugLogControlEpFsmRmtInvErrCode                         Gauge32,
    cucsSysdebugLogControlEpFsmRmtInvErrDescr                        SnmpAdminString,
    cucsSysdebugLogControlEpFsmRmtInvRslt                            CucsConditionRemoteInvRslt,
    cucsSysdebugLogControlEpFsmStageDescr                            SnmpAdminString,
    cucsSysdebugLogControlEpFsmStamp                                 DateAndTime,
    cucsSysdebugLogControlEpFsmStatus                                SnmpAdminString,
    cucsSysdebugLogControlEpFsmTry                                   Gauge32,
    cucsSysdebugLogControlEpLevel                                    CucsSysdebugLogControlLevel,
    cucsSysdebugLogControlEpLevelFlag                                TruthValue,
    cucsSysdebugLogControlEpPersist                                  TruthValue,
    cucsSysdebugLogControlEpReset                                    TruthValue
}

cucsSysdebugLogControlEpInstanceId OBJECT-TYPE
    SYNTAX       CucsManagedObjectId
    MAX-ACCESS   not-accessible
    STATUS       current
    DESCRIPTION
        "Instance identifier of the managed object."
    ::= { cucsSysdebugLogControlEpEntry 1 }

cucsSysdebugLogControlEpDn OBJECT-TYPE
    SYNTAX       CucsManagedObjectDn
    MAX-ACCESS   read-only
    STATUS       current
    DESCRIPTION
        "Cisco UCS sysdebug:LogControlEp:dn managed object property"
    ::= { cucsSysdebugLogControlEpEntry 2 }

cucsSysdebugLogControlEpRn OBJECT-TYPE
    SYNTAX       SnmpAdminString
    MAX-ACCESS   read-only
    STATUS       current
    DESCRIPTION
        "Cisco UCS sysdebug:LogControlEp:rn managed object property"
    ::= { cucsSysdebugLogControlEpEntry 3 }

cucsSysdebugLogControlEpFsmDescr OBJECT-TYPE
    SYNTAX       SnmpAdminString
    MAX-ACCESS   read-only
    STATUS       current
    DESCRIPTION
        "Cisco UCS sysdebug:LogControlEp:fsmDescr managed object property"
    ::= { cucsSysdebugLogControlEpEntry 4 }

cucsSysdebugLogControlEpFsmPrev OBJECT-TYPE
    SYNTAX       SnmpAdminString
    MAX-ACCESS   read-only
    STATUS       current
    DESCRIPTION
        "Cisco UCS sysdebug:LogControlEp:fsmPrev managed object property"
    ::= { cucsSysdebugLogControlEpEntry 5 }

cucsSysdebugLogControlEpFsmProgr OBJECT-TYPE
    SYNTAX       Gauge32
    MAX-ACCESS   read-only
    STATUS       current
    DESCRIPTION
        "Cisco UCS sysdebug:LogControlEp:fsmProgr managed object property"
    ::= { cucsSysdebugLogControlEpEntry 6 }

cucsSysdebugLogControlEpFsmRmtInvErrCode OBJECT-TYPE
    SYNTAX       Gauge32
    MAX-ACCESS   read-only
    STATUS       current
    DESCRIPTION
        "Cisco UCS sysdebug:LogControlEp:fsmRmtInvErrCode
        managed object property"
    ::= { cucsSysdebugLogControlEpEntry 7 }

cucsSysdebugLogControlEpFsmRmtInvErrDescr OBJECT-TYPE
    SYNTAX       SnmpAdminString
    MAX-ACCESS   read-only
    STATUS       current
    DESCRIPTION
        "Cisco UCS sysdebug:LogControlEp:fsmRmtInvErrDescr
        managed object property"
    ::= { cucsSysdebugLogControlEpEntry 8 }

cucsSysdebugLogControlEpFsmRmtInvRslt OBJECT-TYPE
    SYNTAX       CucsConditionRemoteInvRslt
    MAX-ACCESS   read-only
    STATUS       current
    DESCRIPTION
        "Cisco UCS sysdebug:LogControlEp:fsmRmtInvRslt
        managed object property"
    ::= { cucsSysdebugLogControlEpEntry 9 }

cucsSysdebugLogControlEpFsmStageDescr OBJECT-TYPE
    SYNTAX       SnmpAdminString
    MAX-ACCESS   read-only
    STATUS       current
    DESCRIPTION
        "Cisco UCS sysdebug:LogControlEp:fsmStageDescr
        managed object property"
    ::= { cucsSysdebugLogControlEpEntry 10 }

cucsSysdebugLogControlEpFsmStamp OBJECT-TYPE
    SYNTAX       DateAndTime
    MAX-ACCESS   read-only
    STATUS       current
    DESCRIPTION
        "Cisco UCS sysdebug:LogControlEp:fsmStamp managed object property"
    ::= { cucsSysdebugLogControlEpEntry 11 }

cucsSysdebugLogControlEpFsmStatus OBJECT-TYPE
    SYNTAX       SnmpAdminString
    MAX-ACCESS   read-only
    STATUS       current
    DESCRIPTION
        "Cisco UCS sysdebug:LogControlEp:fsmStatus managed
        object property"
    ::= { cucsSysdebugLogControlEpEntry 12 }

cucsSysdebugLogControlEpFsmTry OBJECT-TYPE
    SYNTAX       Gauge32
    MAX-ACCESS   read-only
    STATUS       current
    DESCRIPTION
        "Cisco UCS sysdebug:LogControlEp:fsmTry managed object property"
    ::= { cucsSysdebugLogControlEpEntry 13 }

cucsSysdebugLogControlEpLevel OBJECT-TYPE
    SYNTAX       CucsSysdebugLogControlLevel
    MAX-ACCESS   read-only
    STATUS       current
    DESCRIPTION
        "Cisco UCS sysdebug:LogControlEp:level managed object property"
    ::= { cucsSysdebugLogControlEpEntry 14 }

cucsSysdebugLogControlEpLevelFlag OBJECT-TYPE
    SYNTAX       TruthValue
    MAX-ACCESS   read-only
    STATUS       current
    DESCRIPTION
        "Cisco UCS sysdebug:LogControlEp:levelFlag managed
        object property"
    ::= { cucsSysdebugLogControlEpEntry 15 }

cucsSysdebugLogControlEpPersist OBJECT-TYPE
    SYNTAX       TruthValue
    MAX-ACCESS   read-only
    STATUS       current
    DESCRIPTION
        "Cisco UCS sysdebug:LogControlEp:persist managed object property"
    ::= { cucsSysdebugLogControlEpEntry 16 }

cucsSysdebugLogControlEpReset OBJECT-TYPE
    SYNTAX       TruthValue
    MAX-ACCESS   read-only
    STATUS       current
    DESCRIPTION
        "Cisco UCS sysdebug:LogControlEp:reset managed object property"
    ::= { cucsSysdebugLogControlEpEntry 17 }

cucsSysdebugLogControlEpFsmTaskTable OBJECT-TYPE
    SYNTAX           SEQUENCE OF CucsSysdebugLogControlEpFsmTaskEntry
    MAX-ACCESS       not-accessible
    STATUS           current
    DESCRIPTION
        "Cisco UCS sysdebug:LogControlEpFsmTask managed object table"
    ::= { cucsSysdebugObjects 11 }

cucsSysdebugLogControlEpFsmTaskEntry OBJECT-TYPE
    SYNTAX           CucsSysdebugLogControlEpFsmTaskEntry
    MAX-ACCESS       not-accessible
    STATUS           current
    DESCRIPTION
        "Entry for the cucsSysdebugLogControlEpFsmTaskTable table."
    INDEX { cucsSysdebugLogControlEpFsmTaskInstanceId }
    ::= { cucsSysdebugLogControlEpFsmTaskTable 1 }

CucsSysdebugLogControlEpFsmTaskEntry ::= SEQUENCE {
    cucsSysdebugLogControlEpFsmTaskInstanceId                        CucsManagedObjectId,
    cucsSysdebugLogControlEpFsmTaskDn                                CucsManagedObjectDn,
    cucsSysdebugLogControlEpFsmTaskRn                                SnmpAdminString,
    cucsSysdebugLogControlEpFsmTaskCompletion                        CucsFsmCompletion,
    cucsSysdebugLogControlEpFsmTaskFlags                             CucsFsmFlags,
    cucsSysdebugLogControlEpFsmTaskItem                              CucsSysdebugLogControlEpFsmTaskItem,
    cucsSysdebugLogControlEpFsmTaskSeqId                             Gauge32
}

cucsSysdebugLogControlEpFsmTaskInstanceId OBJECT-TYPE
    SYNTAX       CucsManagedObjectId
    MAX-ACCESS   not-accessible
    STATUS       current
    DESCRIPTION
        "Instance identifier of the managed object."
    ::= { cucsSysdebugLogControlEpFsmTaskEntry 1 }

cucsSysdebugLogControlEpFsmTaskDn OBJECT-TYPE
    SYNTAX       CucsManagedObjectDn
    MAX-ACCESS   read-only
    STATUS       current
    DESCRIPTION
        "Cisco UCS sysdebug:LogControlEpFsmTask:dn managed
        object property"
    ::= { cucsSysdebugLogControlEpFsmTaskEntry 2 }

cucsSysdebugLogControlEpFsmTaskRn OBJECT-TYPE
    SYNTAX       SnmpAdminString
    MAX-ACCESS   read-only
    STATUS       current
    DESCRIPTION
        "Cisco UCS sysdebug:LogControlEpFsmTask:rn managed
        object property"
    ::= { cucsSysdebugLogControlEpFsmTaskEntry 3 }

cucsSysdebugLogControlEpFsmTaskCompletion OBJECT-TYPE
    SYNTAX       CucsFsmCompletion
    MAX-ACCESS   read-only
    STATUS       current
    DESCRIPTION
        "Cisco UCS sysdebug:LogControlEpFsmTask:completion
        managed object property"
    ::= { cucsSysdebugLogControlEpFsmTaskEntry 4 }

cucsSysdebugLogControlEpFsmTaskFlags OBJECT-TYPE
    SYNTAX       CucsFsmFlags
    MAX-ACCESS   read-only
    STATUS       current
    DESCRIPTION
        "Cisco UCS sysdebug:LogControlEpFsmTask:flags managed
        object property"
    ::= { cucsSysdebugLogControlEpFsmTaskEntry 5 }

cucsSysdebugLogControlEpFsmTaskItem OBJECT-TYPE
    SYNTAX       CucsSysdebugLogControlEpFsmTaskItem
    MAX-ACCESS   read-only
    STATUS       current
    DESCRIPTION
        "Cisco UCS sysdebug:LogControlEpFsmTask:item managed
        object property"
    ::= { cucsSysdebugLogControlEpFsmTaskEntry 6 }

cucsSysdebugLogControlEpFsmTaskSeqId OBJECT-TYPE
    SYNTAX       Gauge32
    MAX-ACCESS   read-only
    STATUS       current
    DESCRIPTION
        "Cisco UCS sysdebug:LogControlEpFsmTask:seqId managed
        object property"
    ::= { cucsSysdebugLogControlEpFsmTaskEntry 7 }

cucsSysdebugLogControlModuleTable OBJECT-TYPE
    SYNTAX           SEQUENCE OF CucsSysdebugLogControlModuleEntry
    MAX-ACCESS       not-accessible
    STATUS           current
    DESCRIPTION
        "Cisco UCS sysdebug:LogControlModule managed object table"
    ::= { cucsSysdebugObjects 12 }

cucsSysdebugLogControlModuleEntry OBJECT-TYPE
    SYNTAX           CucsSysdebugLogControlModuleEntry
    MAX-ACCESS       not-accessible
    STATUS           current
    DESCRIPTION
        "Entry for the cucsSysdebugLogControlModuleTable table."
    INDEX { cucsSysdebugLogControlModuleInstanceId }
    ::= { cucsSysdebugLogControlModuleTable 1 }

CucsSysdebugLogControlModuleEntry ::= SEQUENCE {
    cucsSysdebugLogControlModuleInstanceId                           CucsManagedObjectId,
    cucsSysdebugLogControlModuleDn                                   CucsManagedObjectDn,
    cucsSysdebugLogControlModuleRn                                   SnmpAdminString,
    cucsSysdebugLogControlModuleDefaultLevel                         CucsSysdebugLogControlLevel,
    cucsSysdebugLogControlModuleLevel                                CucsSysdebugLogControlLevel,
    cucsSysdebugLogControlModuleName                                 SnmpAdminString,
    cucsSysdebugLogControlModuleReset                                TruthValue
}

cucsSysdebugLogControlModuleInstanceId OBJECT-TYPE
    SYNTAX       CucsManagedObjectId
    MAX-ACCESS   not-accessible
    STATUS       current
    DESCRIPTION
        "Instance identifier of the managed object."
    ::= { cucsSysdebugLogControlModuleEntry 1 }

cucsSysdebugLogControlModuleDn OBJECT-TYPE
    SYNTAX       CucsManagedObjectDn
    MAX-ACCESS   read-only
    STATUS       current
    DESCRIPTION
        "Cisco UCS sysdebug:LogControlModule:dn managed object property"
    ::= { cucsSysdebugLogControlModuleEntry 2 }

cucsSysdebugLogControlModuleRn OBJECT-TYPE
    SYNTAX       SnmpAdminString
    MAX-ACCESS   read-only
    STATUS       current
    DESCRIPTION
        "Cisco UCS sysdebug:LogControlModule:rn managed object property"
    ::= { cucsSysdebugLogControlModuleEntry 3 }

cucsSysdebugLogControlModuleDefaultLevel OBJECT-TYPE
    SYNTAX       CucsSysdebugLogControlLevel
    MAX-ACCESS   read-only
    STATUS       current
    DESCRIPTION
        "Cisco UCS sysdebug:LogControlModule:defaultLevel
        managed object property"
    ::= { cucsSysdebugLogControlModuleEntry 4 }

cucsSysdebugLogControlModuleLevel OBJECT-TYPE
    SYNTAX       CucsSysdebugLogControlLevel
    MAX-ACCESS   read-only
    STATUS       current
    DESCRIPTION
        "Cisco UCS sysdebug:LogControlModule:level managed
        object property"
    ::= { cucsSysdebugLogControlModuleEntry 5 }

cucsSysdebugLogControlModuleName OBJECT-TYPE
    SYNTAX       SnmpAdminString
    MAX-ACCESS   read-only
    STATUS       current
    DESCRIPTION
        "Cisco UCS sysdebug:LogControlModule:name managed object property"
    ::= { cucsSysdebugLogControlModuleEntry 6 }

cucsSysdebugLogControlModuleReset OBJECT-TYPE
    SYNTAX       TruthValue
    MAX-ACCESS   read-only
    STATUS       current
    DESCRIPTION
        "Cisco UCS sysdebug:LogControlModule:reset managed
        object property"
    ::= { cucsSysdebugLogControlModuleEntry 7 }

cucsSysdebugMEpLogTable OBJECT-TYPE
    SYNTAX           SEQUENCE OF CucsSysdebugMEpLogEntry
    MAX-ACCESS       not-accessible
    STATUS           current
    DESCRIPTION
        "Cisco UCS sysdebug:MEpLog managed object table"
    ::= { cucsSysdebugObjects 13 }

cucsSysdebugMEpLogEntry OBJECT-TYPE
    SYNTAX           CucsSysdebugMEpLogEntry
    MAX-ACCESS       not-accessible
    STATUS           current
    DESCRIPTION
        "Entry for the cucsSysdebugMEpLogTable table."
    INDEX { cucsSysdebugMEpLogInstanceId }
    ::= { cucsSysdebugMEpLogTable 1 }

CucsSysdebugMEpLogEntry ::= SEQUENCE {
    cucsSysdebugMEpLogInstanceId                                     CucsManagedObjectId,
    cucsSysdebugMEpLogDn                                             CucsManagedObjectDn,
    cucsSysdebugMEpLogRn                                             SnmpAdminString,
    cucsSysdebugMEpLogAdminState                                     CucsSysdebugEpLogAdminState,
    cucsSysdebugMEpLogCapacity                                       CucsSysdebugEpLogCapacity,
    cucsSysdebugMEpLogId                                             Gauge32,
    cucsSysdebugMEpLogLastUpdate                                     DateAndTime,
    cucsSysdebugMEpLogOperState                                      CucsSysdebugMEpLogOperState,
    cucsSysdebugMEpLogType                                           CucsSysdebugEpLogType
}

cucsSysdebugMEpLogInstanceId OBJECT-TYPE
    SYNTAX       CucsManagedObjectId
    MAX-ACCESS   not-accessible
    STATUS       current
    DESCRIPTION
        "Instance identifier of the managed object."
    ::= { cucsSysdebugMEpLogEntry 1 }

cucsSysdebugMEpLogDn OBJECT-TYPE
    SYNTAX       CucsManagedObjectDn
    MAX-ACCESS   read-only
    STATUS       current
    DESCRIPTION
        "Cisco UCS sysdebug:MEpLog:dn managed object property"
    ::= { cucsSysdebugMEpLogEntry 2 }

cucsSysdebugMEpLogRn OBJECT-TYPE
    SYNTAX       SnmpAdminString
    MAX-ACCESS   read-only
    STATUS       current
    DESCRIPTION
        "Cisco UCS sysdebug:MEpLog:rn managed object property"
    ::= { cucsSysdebugMEpLogEntry 3 }

cucsSysdebugMEpLogAdminState OBJECT-TYPE
    SYNTAX       CucsSysdebugEpLogAdminState
    MAX-ACCESS   read-only
    STATUS       current
    DESCRIPTION
        "Cisco UCS sysdebug:MEpLog:adminState managed object property"
    ::= { cucsSysdebugMEpLogEntry 4 }

cucsSysdebugMEpLogCapacity OBJECT-TYPE
    SYNTAX       CucsSysdebugEpLogCapacity
    MAX-ACCESS   read-only
    STATUS       current
    DESCRIPTION
        "Cisco UCS sysdebug:MEpLog:capacity managed object property"
    ::= { cucsSysdebugMEpLogEntry 5 }

cucsSysdebugMEpLogId OBJECT-TYPE
    SYNTAX       Gauge32
    MAX-ACCESS   read-only
    STATUS       current
    DESCRIPTION
        "Cisco UCS sysdebug:MEpLog:id managed object property"
    ::= { cucsSysdebugMEpLogEntry 6 }

cucsSysdebugMEpLogLastUpdate OBJECT-TYPE
    SYNTAX       DateAndTime
    MAX-ACCESS   read-only
    STATUS       current
    DESCRIPTION
        "Cisco UCS sysdebug:MEpLog:lastUpdate managed object property"
    ::= { cucsSysdebugMEpLogEntry 7 }

cucsSysdebugMEpLogOperState OBJECT-TYPE
    SYNTAX       CucsSysdebugMEpLogOperState
    MAX-ACCESS   read-only
    STATUS       current
    DESCRIPTION
        "Cisco UCS sysdebug:MEpLog:operState managed object property"
    ::= { cucsSysdebugMEpLogEntry 8 }

cucsSysdebugMEpLogType OBJECT-TYPE
    SYNTAX       CucsSysdebugEpLogType
    MAX-ACCESS   read-only
    STATUS       current
    DESCRIPTION
        "Cisco UCS sysdebug:MEpLog:type managed object property"
    ::= { cucsSysdebugMEpLogEntry 9 }

cucsSysdebugMEpLogPolicyTable OBJECT-TYPE
    SYNTAX           SEQUENCE OF CucsSysdebugMEpLogPolicyEntry
    MAX-ACCESS       not-accessible
    STATUS           current
    DESCRIPTION
        "Cisco UCS sysdebug:MEpLogPolicy managed object table"
    ::= { cucsSysdebugObjects 14 }

cucsSysdebugMEpLogPolicyEntry OBJECT-TYPE
    SYNTAX           CucsSysdebugMEpLogPolicyEntry
    MAX-ACCESS       not-accessible
    STATUS           current
    DESCRIPTION
        "Entry for the cucsSysdebugMEpLogPolicyTable table."
    INDEX { cucsSysdebugMEpLogPolicyInstanceId }
    ::= { cucsSysdebugMEpLogPolicyTable 1 }

CucsSysdebugMEpLogPolicyEntry ::= SEQUENCE {
    cucsSysdebugMEpLogPolicyInstanceId                               CucsManagedObjectId,
    cucsSysdebugMEpLogPolicyDn                                       CucsManagedObjectDn,
    cucsSysdebugMEpLogPolicyRn                                       SnmpAdminString,
    cucsSysdebugMEpLogPolicyDescr                                    SnmpAdminString,
    cucsSysdebugMEpLogPolicyIntId                                    SnmpAdminString,
    cucsSysdebugMEpLogPolicyName                                     SnmpAdminString,
    cucsSysdebugMEpLogPolicyType                                     CucsSysdebugEpLogType
}

cucsSysdebugMEpLogPolicyInstanceId OBJECT-TYPE
    SYNTAX       CucsManagedObjectId
    MAX-ACCESS   not-accessible
    STATUS       current
    DESCRIPTION
        "Instance identifier of the managed object."
    ::= { cucsSysdebugMEpLogPolicyEntry 1 }

cucsSysdebugMEpLogPolicyDn OBJECT-TYPE
    SYNTAX       CucsManagedObjectDn
    MAX-ACCESS   read-only
    STATUS       current
    DESCRIPTION
        "Cisco UCS sysdebug:MEpLogPolicy:dn managed object property"
    ::= { cucsSysdebugMEpLogPolicyEntry 2 }

cucsSysdebugMEpLogPolicyRn OBJECT-TYPE
    SYNTAX       SnmpAdminString
    MAX-ACCESS   read-only
    STATUS       current
    DESCRIPTION
        "Cisco UCS sysdebug:MEpLogPolicy:rn managed object property"
    ::= { cucsSysdebugMEpLogPolicyEntry 3 }

cucsSysdebugMEpLogPolicyDescr OBJECT-TYPE
    SYNTAX       SnmpAdminString
    MAX-ACCESS   read-only
    STATUS       current
    DESCRIPTION
        "Cisco UCS sysdebug:MEpLogPolicy:descr managed object property"
    ::= { cucsSysdebugMEpLogPolicyEntry 4 }

cucsSysdebugMEpLogPolicyIntId OBJECT-TYPE
    SYNTAX       SnmpAdminString
    MAX-ACCESS   read-only
    STATUS       current
    DESCRIPTION
        "Cisco UCS sysdebug:MEpLogPolicy:intId managed object property"
    ::= { cucsSysdebugMEpLogPolicyEntry 5 }

cucsSysdebugMEpLogPolicyName OBJECT-TYPE
    SYNTAX       SnmpAdminString
    MAX-ACCESS   read-only
    STATUS       current
    DESCRIPTION
        "Cisco UCS sysdebug:MEpLogPolicy:name managed object property"
    ::= { cucsSysdebugMEpLogPolicyEntry 6 }

cucsSysdebugMEpLogPolicyType OBJECT-TYPE
    SYNTAX       CucsSysdebugEpLogType
    MAX-ACCESS   read-only
    STATUS       current
    DESCRIPTION
        "Cisco UCS sysdebug:MEpLogPolicy:type managed object property"
    ::= { cucsSysdebugMEpLogPolicyEntry 7 }

cucsSysdebugManualCoreFileExportTargetTable OBJECT-TYPE
    SYNTAX           SEQUENCE OF CucsSysdebugManualCoreFileExportTargetEntry
    MAX-ACCESS       not-accessible
    STATUS           current
    DESCRIPTION
        "Cisco UCS sysdebug:ManualCoreFileExportTarget
        managed object table"
    ::= { cucsSysdebugObjects 15 }

cucsSysdebugManualCoreFileExportTargetEntry OBJECT-TYPE
    SYNTAX           CucsSysdebugManualCoreFileExportTargetEntry
    MAX-ACCESS       not-accessible
    STATUS           current
    DESCRIPTION
        "Entry for the cucsSysdebugManualCoreFileExportTargetTable table."
    INDEX { cucsSysdebugManualCoreFileExportTargetInstanceId }
    ::= { cucsSysdebugManualCoreFileExportTargetTable 1 }

CucsSysdebugManualCoreFileExportTargetEntry ::= SEQUENCE {
    cucsSysdebugManualCoreFileExportTargetInstanceId                 CucsManagedObjectId,
    cucsSysdebugManualCoreFileExportTargetDn                         CucsManagedObjectDn,
    cucsSysdebugManualCoreFileExportTargetRn                         SnmpAdminString,
    cucsSysdebugManualCoreFileExportTargetAdminState                 CucsSysdebugManualCoreFileExportTargetAdminState,
    cucsSysdebugManualCoreFileExportTargetDescr                      SnmpAdminString,
    cucsSysdebugManualCoreFileExportTargetFsmDescr                   SnmpAdminString,
    cucsSysdebugManualCoreFileExportTargetFsmPrev                    SnmpAdminString,
    cucsSysdebugManualCoreFileExportTargetFsmProgr                   Gauge32,
    cucsSysdebugManualCoreFileExportTargetFsmRmtInvErrCode           Gauge32,
    cucsSysdebugManualCoreFileExportTargetFsmRmtInvErrDescr          SnmpAdminString,
    cucsSysdebugManualCoreFileExportTargetFsmRmtInvRslt              CucsConditionRemoteInvRslt,
    cucsSysdebugManualCoreFileExportTargetFsmStageDescr              SnmpAdminString,
    cucsSysdebugManualCoreFileExportTargetFsmStamp                   DateAndTime,
    cucsSysdebugManualCoreFileExportTargetFsmStatus                  SnmpAdminString,
    cucsSysdebugManualCoreFileExportTargetFsmTry                     Gauge32,
    cucsSysdebugManualCoreFileExportTargetHostname                   SnmpAdminString,
    cucsSysdebugManualCoreFileExportTargetIntId                      SnmpAdminString,
    cucsSysdebugManualCoreFileExportTargetName                       SnmpAdminString,
    cucsSysdebugManualCoreFileExportTargetPath                       SnmpAdminString,
    cucsSysdebugManualCoreFileExportTargetPort                       Gauge32,
    cucsSysdebugManualCoreFileExportTargetPostAction                 CucsSysfileExporterPostAction,
    cucsSysdebugManualCoreFileExportTargetProto                      CucsSysdebugManualCoreFileExportTargetProto,
    cucsSysdebugManualCoreFileExportTargetExportFailureReason        SnmpAdminString,
    cucsSysdebugManualCoreFileExportTargetExportStatus               CucsSysdebugCoreExportStatus
}

cucsSysdebugManualCoreFileExportTargetInstanceId OBJECT-TYPE
    SYNTAX       CucsManagedObjectId
    MAX-ACCESS   not-accessible
    STATUS       current
    DESCRIPTION
        "Instance identifier of the managed object."
    ::= { cucsSysdebugManualCoreFileExportTargetEntry 1 }

cucsSysdebugManualCoreFileExportTargetDn OBJECT-TYPE
    SYNTAX       CucsManagedObjectDn
    MAX-ACCESS   read-only
    STATUS       current
    DESCRIPTION
        "Cisco UCS sysdebug:ManualCoreFileExportTarget:dn
        managed object property"
    ::= { cucsSysdebugManualCoreFileExportTargetEntry 2 }

cucsSysdebugManualCoreFileExportTargetRn OBJECT-TYPE
    SYNTAX       SnmpAdminString
    MAX-ACCESS   read-only
    STATUS       current
    DESCRIPTION
        "Cisco UCS sysdebug:ManualCoreFileExportTarget:rn
        managed object property"
    ::= { cucsSysdebugManualCoreFileExportTargetEntry 3 }

cucsSysdebugManualCoreFileExportTargetAdminState OBJECT-TYPE
    SYNTAX       CucsSysdebugManualCoreFileExportTargetAdminState
    MAX-ACCESS   read-only
    STATUS       current
    DESCRIPTION
        "Cisco UCS sysdebug:ManualCoreFileExportTarget:adminState
        managed object property"
    ::= { cucsSysdebugManualCoreFileExportTargetEntry 4 }

cucsSysdebugManualCoreFileExportTargetDescr OBJECT-TYPE
    SYNTAX       SnmpAdminString
    MAX-ACCESS   read-only
    STATUS       current
    DESCRIPTION
        "Cisco UCS sysdebug:ManualCoreFileExportTarget:descr
        managed object property"
    ::= { cucsSysdebugManualCoreFileExportTargetEntry 5 }

cucsSysdebugManualCoreFileExportTargetFsmDescr OBJECT-TYPE
    SYNTAX       SnmpAdminString
    MAX-ACCESS   read-only
    STATUS       current
    DESCRIPTION
        "Cisco UCS sysdebug:ManualCoreFileExportTarget:fsmDescr
        managed object property"
    ::= { cucsSysdebugManualCoreFileExportTargetEntry 6 }

cucsSysdebugManualCoreFileExportTargetFsmPrev OBJECT-TYPE
    SYNTAX       SnmpAdminString
    MAX-ACCESS   read-only
    STATUS       current
    DESCRIPTION
        "Cisco UCS sysdebug:ManualCoreFileExportTarget:fsmPrev
        managed object property"
    ::= { cucsSysdebugManualCoreFileExportTargetEntry 7 }

cucsSysdebugManualCoreFileExportTargetFsmProgr OBJECT-TYPE
    SYNTAX       Gauge32
    MAX-ACCESS   read-only
    STATUS       current
    DESCRIPTION
        "Cisco UCS sysdebug:ManualCoreFileExportTarget:fsmProgr
        managed object property"
    ::= { cucsSysdebugManualCoreFileExportTargetEntry 8 }

cucsSysdebugManualCoreFileExportTargetFsmRmtInvErrCode OBJECT-TYPE
    SYNTAX       Gauge32
    MAX-ACCESS   read-only
    STATUS       current
    DESCRIPTION
        "Cisco UCS sysdebug:ManualCoreFileExportTarget:fsmRmtInvErrCode
        managed object property"
    ::= { cucsSysdebugManualCoreFileExportTargetEntry 9 }

cucsSysdebugManualCoreFileExportTargetFsmRmtInvErrDescr OBJECT-TYPE
    SYNTAX       SnmpAdminString
    MAX-ACCESS   read-only
    STATUS       current
    DESCRIPTION
        "Cisco UCS sysdebug:ManualCoreFileExportTarget:fsmRmtInvErrDescr
        managed object property"
    ::= { cucsSysdebugManualCoreFileExportTargetEntry 10 }

cucsSysdebugManualCoreFileExportTargetFsmRmtInvRslt OBJECT-TYPE
    SYNTAX       CucsConditionRemoteInvRslt
    MAX-ACCESS   read-only
    STATUS       current
    DESCRIPTION
        "Cisco UCS sysdebug:ManualCoreFileExportTarget:fsmRmtInvRslt
        managed object property"
    ::= { cucsSysdebugManualCoreFileExportTargetEntry 11 }

cucsSysdebugManualCoreFileExportTargetFsmStageDescr OBJECT-TYPE
    SYNTAX       SnmpAdminString
    MAX-ACCESS   read-only
    STATUS       current
    DESCRIPTION
        "Cisco UCS sysdebug:ManualCoreFileExportTarget:fsmStageDescr
        managed object property"
    ::= { cucsSysdebugManualCoreFileExportTargetEntry 12 }

cucsSysdebugManualCoreFileExportTargetFsmStamp OBJECT-TYPE
    SYNTAX       DateAndTime
    MAX-ACCESS   read-only
    STATUS       current
    DESCRIPTION
        "Cisco UCS sysdebug:ManualCoreFileExportTarget:fsmStamp
        managed object property"
    ::= { cucsSysdebugManualCoreFileExportTargetEntry 13 }

cucsSysdebugManualCoreFileExportTargetFsmStatus OBJECT-TYPE
    SYNTAX       SnmpAdminString
    MAX-ACCESS   read-only
    STATUS       current
    DESCRIPTION
        "Cisco UCS sysdebug:ManualCoreFileExportTarget:fsmStatus
        managed object property"
    ::= { cucsSysdebugManualCoreFileExportTargetEntry 14 }

cucsSysdebugManualCoreFileExportTargetFsmTry OBJECT-TYPE
    SYNTAX       Gauge32
    MAX-ACCESS   read-only
    STATUS       current
    DESCRIPTION
        "Cisco UCS sysdebug:ManualCoreFileExportTarget:fsmTry
        managed object property"
    ::= { cucsSysdebugManualCoreFileExportTargetEntry 15 }

cucsSysdebugManualCoreFileExportTargetHostname OBJECT-TYPE
    SYNTAX       SnmpAdminString
    MAX-ACCESS   read-only
    STATUS       current
    DESCRIPTION
        "Cisco UCS sysdebug:ManualCoreFileExportTarget:hostname
        managed object property"
    ::= { cucsSysdebugManualCoreFileExportTargetEntry 16 }

cucsSysdebugManualCoreFileExportTargetIntId OBJECT-TYPE
    SYNTAX       SnmpAdminString
    MAX-ACCESS   read-only
    STATUS       current
    DESCRIPTION
        "Cisco UCS sysdebug:ManualCoreFileExportTarget:intId
        managed object property"
    ::= { cucsSysdebugManualCoreFileExportTargetEntry 17 }

cucsSysdebugManualCoreFileExportTargetName OBJECT-TYPE
    SYNTAX       SnmpAdminString
    MAX-ACCESS   read-only
    STATUS       current
    DESCRIPTION
        "Cisco UCS sysdebug:ManualCoreFileExportTarget:name
        managed object property"
    ::= { cucsSysdebugManualCoreFileExportTargetEntry 18 }

cucsSysdebugManualCoreFileExportTargetPath OBJECT-TYPE
    SYNTAX       SnmpAdminString
    MAX-ACCESS   read-only
    STATUS       current
    DESCRIPTION
        "Cisco UCS sysdebug:ManualCoreFileExportTarget:path
        managed object property"
    ::= { cucsSysdebugManualCoreFileExportTargetEntry 19 }

cucsSysdebugManualCoreFileExportTargetPort OBJECT-TYPE
    SYNTAX       Gauge32
    MAX-ACCESS   read-only
    STATUS       current
    DESCRIPTION
        "Cisco UCS sysdebug:ManualCoreFileExportTarget:port
        managed object property"
    ::= { cucsSysdebugManualCoreFileExportTargetEntry 20 }

cucsSysdebugManualCoreFileExportTargetPostAction OBJECT-TYPE
    SYNTAX       CucsSysfileExporterPostAction
    MAX-ACCESS   read-only
    STATUS       current
    DESCRIPTION
        "Cisco UCS sysdebug:ManualCoreFileExportTarget:postAction
        managed object property"
    ::= { cucsSysdebugManualCoreFileExportTargetEntry 21 }

cucsSysdebugManualCoreFileExportTargetProto OBJECT-TYPE
    SYNTAX       CucsSysdebugManualCoreFileExportTargetProto
    MAX-ACCESS   read-only
    STATUS       current
    DESCRIPTION
        "Cisco UCS sysdebug:ManualCoreFileExportTarget:proto
        managed object property"
    ::= { cucsSysdebugManualCoreFileExportTargetEntry 22 }

cucsSysdebugManualCoreFileExportTargetExportFailureReason OBJECT-TYPE
    SYNTAX       SnmpAdminString
    MAX-ACCESS   read-only
    STATUS       current
    DESCRIPTION
        "Cisco UCS sysdebug:ManualCoreFileExportTarget:exportFailureReason
         managed object property"
    ::= { cucsSysdebugManualCoreFileExportTargetEntry 23 }

cucsSysdebugManualCoreFileExportTargetExportStatus OBJECT-TYPE
    SYNTAX       CucsSysdebugCoreExportStatus
    MAX-ACCESS   read-only
    STATUS       current
    DESCRIPTION
        "Cisco UCS sysdebug:ManualCoreFileExportTarget:exportStatus
        managed object property"
    ::= { cucsSysdebugManualCoreFileExportTargetEntry 24 }

cucsSysdebugManualCoreFileExportTargetFsmTaskTable OBJECT-TYPE
    SYNTAX           SEQUENCE OF CucsSysdebugManualCoreFileExportTargetFsmTaskEntry
    MAX-ACCESS       not-accessible
    STATUS           current
    DESCRIPTION
        "Cisco UCS sysdebug:ManualCoreFileExportTargetFsmTask
        managed object table"
    ::= { cucsSysdebugObjects 16 }

cucsSysdebugManualCoreFileExportTargetFsmTaskEntry OBJECT-TYPE
    SYNTAX           CucsSysdebugManualCoreFileExportTargetFsmTaskEntry
    MAX-ACCESS       not-accessible
    STATUS           current
    DESCRIPTION
        "Entry for the cucsSysdebugManualCoreFileExportTargetFsmTaskTable table."
    INDEX { cucsSysdebugManualCoreFileExportTargetFsmTaskInstanceId }
    ::= { cucsSysdebugManualCoreFileExportTargetFsmTaskTable 1 }

CucsSysdebugManualCoreFileExportTargetFsmTaskEntry ::= SEQUENCE {
    cucsSysdebugManualCoreFileExportTargetFsmTaskInstanceId          CucsManagedObjectId,
    cucsSysdebugManualCoreFileExportTargetFsmTaskDn                  CucsManagedObjectDn,
    cucsSysdebugManualCoreFileExportTargetFsmTaskRn                  SnmpAdminString,
    cucsSysdebugManualCoreFileExportTargetFsmTaskCompletion          CucsFsmCompletion,
    cucsSysdebugManualCoreFileExportTargetFsmTaskFlags               CucsFsmFlags,
    cucsSysdebugManualCoreFileExportTargetFsmTaskItem                CucsSysdebugManualCoreFileExportTargetFsmTaskItem,
    cucsSysdebugManualCoreFileExportTargetFsmTaskSeqId               Gauge32
}

cucsSysdebugManualCoreFileExportTargetFsmTaskInstanceId OBJECT-TYPE
    SYNTAX       CucsManagedObjectId
    MAX-ACCESS   not-accessible
    STATUS       current
    DESCRIPTION
        "Instance identifier of the managed object."
    ::= { cucsSysdebugManualCoreFileExportTargetFsmTaskEntry 1 }

cucsSysdebugManualCoreFileExportTargetFsmTaskDn OBJECT-TYPE
    SYNTAX       CucsManagedObjectDn
    MAX-ACCESS   read-only
    STATUS       current
    DESCRIPTION
        "Cisco UCS sysdebug:ManualCoreFileExportTargetFsmTask:dn
        managed object property"
    ::= { cucsSysdebugManualCoreFileExportTargetFsmTaskEntry 2 }

cucsSysdebugManualCoreFileExportTargetFsmTaskRn OBJECT-TYPE
    SYNTAX       SnmpAdminString
    MAX-ACCESS   read-only
    STATUS       current
    DESCRIPTION
        "Cisco UCS sysdebug:ManualCoreFileExportTargetFsmTask:rn
        managed object property"
    ::= { cucsSysdebugManualCoreFileExportTargetFsmTaskEntry 3 }

cucsSysdebugManualCoreFileExportTargetFsmTaskCompletion OBJECT-TYPE
    SYNTAX       CucsFsmCompletion
    MAX-ACCESS   read-only
    STATUS       current
    DESCRIPTION
        "Cisco UCS sysdebug:ManualCoreFileExportTargetFsmTask:completion
        managed object property"
    ::= { cucsSysdebugManualCoreFileExportTargetFsmTaskEntry 4 }

cucsSysdebugManualCoreFileExportTargetFsmTaskFlags OBJECT-TYPE
    SYNTAX       CucsFsmFlags
    MAX-ACCESS   read-only
    STATUS       current
    DESCRIPTION
        "Cisco UCS sysdebug:ManualCoreFileExportTargetFsmTask:flags
        managed object property"
    ::= { cucsSysdebugManualCoreFileExportTargetFsmTaskEntry 5 }

cucsSysdebugManualCoreFileExportTargetFsmTaskItem OBJECT-TYPE
    SYNTAX       CucsSysdebugManualCoreFileExportTargetFsmTaskItem
    MAX-ACCESS   read-only
    STATUS       current
    DESCRIPTION
        "Cisco UCS sysdebug:ManualCoreFileExportTargetFsmTask:item
        managed object property"
    ::= { cucsSysdebugManualCoreFileExportTargetFsmTaskEntry 6 }

cucsSysdebugManualCoreFileExportTargetFsmTaskSeqId OBJECT-TYPE
    SYNTAX       Gauge32
    MAX-ACCESS   read-only
    STATUS       current
    DESCRIPTION
        "Cisco UCS sysdebug:ManualCoreFileExportTargetFsmTask:seqId
        managed object property"
    ::= { cucsSysdebugManualCoreFileExportTargetFsmTaskEntry 7 }

cucsSysdebugTechSupFileRepositoryTable OBJECT-TYPE
    SYNTAX           SEQUENCE OF CucsSysdebugTechSupFileRepositoryEntry
    MAX-ACCESS       not-accessible
    STATUS           current
    DESCRIPTION
        "Cisco UCS sysdebug:TechSupFileRepository managed object table"
    ::= { cucsSysdebugObjects 17 }

cucsSysdebugTechSupFileRepositoryEntry OBJECT-TYPE
    SYNTAX           CucsSysdebugTechSupFileRepositoryEntry
    MAX-ACCESS       not-accessible
    STATUS           current
    DESCRIPTION
        "Entry for the cucsSysdebugTechSupFileRepositoryTable table."
    INDEX { cucsSysdebugTechSupFileRepositoryInstanceId }
    ::= { cucsSysdebugTechSupFileRepositoryTable 1 }

CucsSysdebugTechSupFileRepositoryEntry ::= SEQUENCE {
    cucsSysdebugTechSupFileRepositoryInstanceId                      CucsManagedObjectId,
    cucsSysdebugTechSupFileRepositoryDn                              CucsManagedObjectDn,
    cucsSysdebugTechSupFileRepositoryRn                              SnmpAdminString
}

cucsSysdebugTechSupFileRepositoryInstanceId OBJECT-TYPE
    SYNTAX       CucsManagedObjectId
    MAX-ACCESS   not-accessible
    STATUS       current
    DESCRIPTION
        "Instance identifier of the managed object."
    ::= { cucsSysdebugTechSupFileRepositoryEntry 1 }

cucsSysdebugTechSupFileRepositoryDn OBJECT-TYPE
    SYNTAX       CucsManagedObjectDn
    MAX-ACCESS   read-only
    STATUS       current
    DESCRIPTION
        "Cisco UCS sysdebug:TechSupFileRepository:dn managed
        object property"
    ::= { cucsSysdebugTechSupFileRepositoryEntry 2 }

cucsSysdebugTechSupFileRepositoryRn OBJECT-TYPE
    SYNTAX       SnmpAdminString
    MAX-ACCESS   read-only
    STATUS       current
    DESCRIPTION
        "Cisco UCS sysdebug:TechSupFileRepository:rn managed
        object property"
    ::= { cucsSysdebugTechSupFileRepositoryEntry 3 }

cucsSysdebugTechSupportTable OBJECT-TYPE
    SYNTAX           SEQUENCE OF CucsSysdebugTechSupportEntry
    MAX-ACCESS       not-accessible
    STATUS           current
    DESCRIPTION
        "Cisco UCS sysdebug:TechSupport managed object table"
    ::= { cucsSysdebugObjects 18 }

cucsSysdebugTechSupportEntry OBJECT-TYPE
    SYNTAX           CucsSysdebugTechSupportEntry
    MAX-ACCESS       not-accessible
    STATUS           current
    DESCRIPTION
        "Entry for the cucsSysdebugTechSupportTable table."
    INDEX { cucsSysdebugTechSupportInstanceId }
    ::= { cucsSysdebugTechSupportTable 1 }

CucsSysdebugTechSupportEntry ::= SEQUENCE {
    cucsSysdebugTechSupportInstanceId                                CucsManagedObjectId,
    cucsSysdebugTechSupportDn                                        CucsManagedObjectDn,
    cucsSysdebugTechSupportRn                                        SnmpAdminString,
    cucsSysdebugTechSupportAdminState                                CucsSysdebugTechSupportAdminState,
    cucsSysdebugTechSupportDescr                                     SnmpAdminString,
    cucsSysdebugTechSupportFsmDescr                                  SnmpAdminString,
    cucsSysdebugTechSupportFsmPrev                                   SnmpAdminString,
    cucsSysdebugTechSupportFsmProgr                                  Gauge32,
    cucsSysdebugTechSupportFsmRmtInvErrCode                          Gauge32,
    cucsSysdebugTechSupportFsmRmtInvErrDescr                         SnmpAdminString,
    cucsSysdebugTechSupportFsmRmtInvRslt                             CucsConditionRemoteInvRslt,
    cucsSysdebugTechSupportFsmStageDescr                             SnmpAdminString,
    cucsSysdebugTechSupportFsmStamp                                  DateAndTime,
    cucsSysdebugTechSupportFsmStatus                                 SnmpAdminString,
    cucsSysdebugTechSupportFsmTry                                    Gauge32,
    cucsSysdebugTechSupportName                                      SnmpAdminString,
    cucsSysdebugTechSupportOperState                                 CucsSysdebugTechSupportOperState,
    cucsSysdebugTechSupportSize                                      Gauge32,
    cucsSysdebugTechSupportSwitchId                                  CucsNetworkSwitchId,
    cucsSysdebugTechSupportTs                                        DateAndTime,
    cucsSysdebugTechSupportUri                                       SnmpAdminString,
    cucsSysdebugTechSupportCreationTS                                Unsigned64
}

cucsSysdebugTechSupportInstanceId OBJECT-TYPE
    SYNTAX       CucsManagedObjectId
    MAX-ACCESS   not-accessible
    STATUS       current
    DESCRIPTION
        "Instance identifier of the managed object."
    ::= { cucsSysdebugTechSupportEntry 1 }

cucsSysdebugTechSupportDn OBJECT-TYPE
    SYNTAX       CucsManagedObjectDn
    MAX-ACCESS   read-only
    STATUS       current
    DESCRIPTION
        "Cisco UCS sysdebug:TechSupport:dn managed object property"
    ::= { cucsSysdebugTechSupportEntry 2 }

cucsSysdebugTechSupportRn OBJECT-TYPE
    SYNTAX       SnmpAdminString
    MAX-ACCESS   read-only
    STATUS       current
    DESCRIPTION
        "Cisco UCS sysdebug:TechSupport:rn managed object property"
    ::= { cucsSysdebugTechSupportEntry 3 }

cucsSysdebugTechSupportAdminState OBJECT-TYPE
    SYNTAX       CucsSysdebugTechSupportAdminState
    MAX-ACCESS   read-only
    STATUS       current
    DESCRIPTION
        "Cisco UCS sysdebug:TechSupport:adminState managed
        object property"
    ::= { cucsSysdebugTechSupportEntry 4 }

cucsSysdebugTechSupportDescr OBJECT-TYPE
    SYNTAX       SnmpAdminString
    MAX-ACCESS   read-only
    STATUS       current
    DESCRIPTION
        "Cisco UCS sysdebug:TechSupport:descr managed object property"
    ::= { cucsSysdebugTechSupportEntry 5 }

cucsSysdebugTechSupportFsmDescr OBJECT-TYPE
    SYNTAX       SnmpAdminString
    MAX-ACCESS   read-only
    STATUS       current
    DESCRIPTION
        "Cisco UCS sysdebug:TechSupport:fsmDescr managed object property"
    ::= { cucsSysdebugTechSupportEntry 6 }

cucsSysdebugTechSupportFsmPrev OBJECT-TYPE
    SYNTAX       SnmpAdminString
    MAX-ACCESS   read-only
    STATUS       current
    DESCRIPTION
        "Cisco UCS sysdebug:TechSupport:fsmPrev managed object property"
    ::= { cucsSysdebugTechSupportEntry 7 }

cucsSysdebugTechSupportFsmProgr OBJECT-TYPE
    SYNTAX       Gauge32
    MAX-ACCESS   read-only
    STATUS       current
    DESCRIPTION
        "Cisco UCS sysdebug:TechSupport:fsmProgr managed object property"
    ::= { cucsSysdebugTechSupportEntry 8 }

cucsSysdebugTechSupportFsmRmtInvErrCode OBJECT-TYPE
    SYNTAX       Gauge32
    MAX-ACCESS   read-only
    STATUS       current
    DESCRIPTION
        "Cisco UCS sysdebug:TechSupport:fsmRmtInvErrCode
        managed object property"
    ::= { cucsSysdebugTechSupportEntry 9 }

cucsSysdebugTechSupportFsmRmtInvErrDescr OBJECT-TYPE
    SYNTAX       SnmpAdminString
    MAX-ACCESS   read-only
    STATUS       current
    DESCRIPTION
        "Cisco UCS sysdebug:TechSupport:fsmRmtInvErrDescr
        managed object property"
    ::= { cucsSysdebugTechSupportEntry 10 }

cucsSysdebugTechSupportFsmRmtInvRslt OBJECT-TYPE
    SYNTAX       CucsConditionRemoteInvRslt
    MAX-ACCESS   read-only
    STATUS       current
    DESCRIPTION
        "Cisco UCS sysdebug:TechSupport:fsmRmtInvRslt managed
        object property"
    ::= { cucsSysdebugTechSupportEntry 11 }

cucsSysdebugTechSupportFsmStageDescr OBJECT-TYPE
    SYNTAX       SnmpAdminString
    MAX-ACCESS   read-only
    STATUS       current
    DESCRIPTION
        "Cisco UCS sysdebug:TechSupport:fsmStageDescr managed
        object property"
    ::= { cucsSysdebugTechSupportEntry 12 }

cucsSysdebugTechSupportFsmStamp OBJECT-TYPE
    SYNTAX       DateAndTime
    MAX-ACCESS   read-only
    STATUS       current
    DESCRIPTION
        "Cisco UCS sysdebug:TechSupport:fsmStamp managed object property"
    ::= { cucsSysdebugTechSupportEntry 13 }

cucsSysdebugTechSupportFsmStatus OBJECT-TYPE
    SYNTAX       SnmpAdminString
    MAX-ACCESS   read-only
    STATUS       current
    DESCRIPTION
        "Cisco UCS sysdebug:TechSupport:fsmStatus managed object property"
    ::= { cucsSysdebugTechSupportEntry 14 }

cucsSysdebugTechSupportFsmTry OBJECT-TYPE
    SYNTAX       Gauge32
    MAX-ACCESS   read-only
    STATUS       current
    DESCRIPTION
        "Cisco UCS sysdebug:TechSupport:fsmTry managed object property"
    ::= { cucsSysdebugTechSupportEntry 15 }

cucsSysdebugTechSupportName OBJECT-TYPE
    SYNTAX       SnmpAdminString
    MAX-ACCESS   read-only
    STATUS       current
    DESCRIPTION
        "Cisco UCS sysdebug:TechSupport:name managed object property"
    ::= { cucsSysdebugTechSupportEntry 16 }

cucsSysdebugTechSupportOperState OBJECT-TYPE
    SYNTAX       CucsSysdebugTechSupportOperState
    MAX-ACCESS   read-only
    STATUS       current
    DESCRIPTION
        "Cisco UCS sysdebug:TechSupport:operState managed object property"
    ::= { cucsSysdebugTechSupportEntry 17 }

cucsSysdebugTechSupportSize OBJECT-TYPE
    SYNTAX       Gauge32
    MAX-ACCESS   read-only
    STATUS       current
    DESCRIPTION
        "Cisco UCS sysdebug:TechSupport:size managed object property"
    ::= { cucsSysdebugTechSupportEntry 18 }

cucsSysdebugTechSupportSwitchId OBJECT-TYPE
    SYNTAX       CucsNetworkSwitchId
    MAX-ACCESS   read-only
    STATUS       current
    DESCRIPTION
        "Cisco UCS sysdebug:TechSupport:switchId managed object property"
    ::= { cucsSysdebugTechSupportEntry 19 }

cucsSysdebugTechSupportTs OBJECT-TYPE
    SYNTAX       DateAndTime
    MAX-ACCESS   read-only
    STATUS       current
    DESCRIPTION
        "Cisco UCS sysdebug:TechSupport:ts managed object property"
    ::= { cucsSysdebugTechSupportEntry 20 }

cucsSysdebugTechSupportUri OBJECT-TYPE
    SYNTAX       SnmpAdminString
    MAX-ACCESS   read-only
    STATUS       current
    DESCRIPTION
        "Cisco UCS sysdebug:TechSupport:uri managed object property"
    ::= { cucsSysdebugTechSupportEntry 21 }

cucsSysdebugTechSupportCreationTS OBJECT-TYPE
    SYNTAX       Unsigned64
    MAX-ACCESS   read-only
    STATUS       current
    DESCRIPTION
        "Cisco UCS sysdebug:TechSupport:creationTS managed
        object property"
    ::= { cucsSysdebugTechSupportEntry 22 }

cucsSysdebugTechSupportCmdOptTable OBJECT-TYPE
    SYNTAX           SEQUENCE OF CucsSysdebugTechSupportCmdOptEntry
    MAX-ACCESS       not-accessible
    STATUS           current
    DESCRIPTION
        "Cisco UCS sysdebug:TechSupportCmdOpt managed object table"
    ::= { cucsSysdebugObjects 19 }

cucsSysdebugTechSupportCmdOptEntry OBJECT-TYPE
    SYNTAX           CucsSysdebugTechSupportCmdOptEntry
    MAX-ACCESS       not-accessible
    STATUS           current
    DESCRIPTION
        "Entry for the cucsSysdebugTechSupportCmdOptTable table."
    INDEX { cucsSysdebugTechSupportCmdOptInstanceId }
    ::= { cucsSysdebugTechSupportCmdOptTable 1 }

CucsSysdebugTechSupportCmdOptEntry ::= SEQUENCE {
    cucsSysdebugTechSupportCmdOptInstanceId                          CucsManagedObjectId,
    cucsSysdebugTechSupportCmdOptDn                                  CucsManagedObjectDn,
    cucsSysdebugTechSupportCmdOptRn                                  SnmpAdminString,
    cucsSysdebugTechSupportCmdOptChassisCimcId                       Gauge32,
    cucsSysdebugTechSupportCmdOptChassisId                           Gauge32,
    cucsSysdebugTechSupportCmdOptChassisIomId                        Gauge32,
    cucsSysdebugTechSupportCmdOptCimcAdapterId                       Gauge32,
    cucsSysdebugTechSupportCmdOptFabExtId                            Gauge32,
    cucsSysdebugTechSupportCmdOptMajorOptType                        CucsSysdebugTSCmdOptMajorType,
    cucsSysdebugTechSupportCmdOptRackServerAdapterId                 Gauge32,
    cucsSysdebugTechSupportCmdOptRackServerId                        Gauge32
}

cucsSysdebugTechSupportCmdOptInstanceId OBJECT-TYPE
    SYNTAX       CucsManagedObjectId
    MAX-ACCESS   not-accessible
    STATUS       current
    DESCRIPTION
        "Instance identifier of the managed object."
    ::= { cucsSysdebugTechSupportCmdOptEntry 1 }

cucsSysdebugTechSupportCmdOptDn OBJECT-TYPE
    SYNTAX       CucsManagedObjectDn
    MAX-ACCESS   read-only
    STATUS       current
    DESCRIPTION
        "Cisco UCS sysdebug:TechSupportCmdOpt:dn managed object property"
    ::= { cucsSysdebugTechSupportCmdOptEntry 2 }

cucsSysdebugTechSupportCmdOptRn OBJECT-TYPE
    SYNTAX       SnmpAdminString
    MAX-ACCESS   read-only
    STATUS       current
    DESCRIPTION
        "Cisco UCS sysdebug:TechSupportCmdOpt:rn managed object property"
    ::= { cucsSysdebugTechSupportCmdOptEntry 3 }

cucsSysdebugTechSupportCmdOptChassisCimcId OBJECT-TYPE
    SYNTAX       Gauge32
    MAX-ACCESS   read-only
    STATUS       current
    DESCRIPTION
        "Cisco UCS sysdebug:TechSupportCmdOpt:chassisCimcId
        managed object property"
    ::= { cucsSysdebugTechSupportCmdOptEntry 4 }

cucsSysdebugTechSupportCmdOptChassisId OBJECT-TYPE
    SYNTAX       Gauge32
    MAX-ACCESS   read-only
    STATUS       current
    DESCRIPTION
        "Cisco UCS sysdebug:TechSupportCmdOpt:chassisId
        managed object property"
    ::= { cucsSysdebugTechSupportCmdOptEntry 5 }

cucsSysdebugTechSupportCmdOptChassisIomId OBJECT-TYPE
    SYNTAX       Gauge32
    MAX-ACCESS   read-only
    STATUS       current
    DESCRIPTION
        "Cisco UCS sysdebug:TechSupportCmdOpt:chassisIomId
        managed object property"
    ::= { cucsSysdebugTechSupportCmdOptEntry 6 }

cucsSysdebugTechSupportCmdOptCimcAdapterId OBJECT-TYPE
    SYNTAX       Gauge32
    MAX-ACCESS   read-only
    STATUS       current
    DESCRIPTION
        "Cisco UCS sysdebug:TechSupportCmdOpt:cimcAdapterId
        managed object property"
    ::= { cucsSysdebugTechSupportCmdOptEntry 7 }

cucsSysdebugTechSupportCmdOptFabExtId OBJECT-TYPE
    SYNTAX       Gauge32
    MAX-ACCESS   read-only
    STATUS       current
    DESCRIPTION
        "Cisco UCS sysdebug:TechSupportCmdOpt:fabExtId
        managed object property"
    ::= { cucsSysdebugTechSupportCmdOptEntry 8 }

cucsSysdebugTechSupportCmdOptMajorOptType OBJECT-TYPE
    SYNTAX       CucsSysdebugTSCmdOptMajorType
    MAX-ACCESS   read-only
    STATUS       current
    DESCRIPTION
        "Cisco UCS sysdebug:TechSupportCmdOpt:majorOptType
        managed object property"
    ::= { cucsSysdebugTechSupportCmdOptEntry 9 }

cucsSysdebugTechSupportCmdOptRackServerAdapterId OBJECT-TYPE
    SYNTAX       Gauge32
    MAX-ACCESS   read-only
    STATUS       current
    DESCRIPTION
        "Cisco UCS sysdebug:TechSupportCmdOpt:rackServerAdapterId
        managed object property"
    ::= { cucsSysdebugTechSupportCmdOptEntry 10 }

cucsSysdebugTechSupportCmdOptRackServerId OBJECT-TYPE
    SYNTAX       Gauge32
    MAX-ACCESS   read-only
    STATUS       current
    DESCRIPTION
        "Cisco UCS sysdebug:TechSupportCmdOpt:rackServerId
        managed object property"
    ::= { cucsSysdebugTechSupportCmdOptEntry 11 }

cucsSysdebugTechSupportFsmTaskTable OBJECT-TYPE
    SYNTAX           SEQUENCE OF CucsSysdebugTechSupportFsmTaskEntry
    MAX-ACCESS       not-accessible
    STATUS           current
    DESCRIPTION
        "Cisco UCS sysdebug:TechSupportFsmTask managed object table"
    ::= { cucsSysdebugObjects 20 }

cucsSysdebugTechSupportFsmTaskEntry OBJECT-TYPE
    SYNTAX           CucsSysdebugTechSupportFsmTaskEntry
    MAX-ACCESS       not-accessible
    STATUS           current
    DESCRIPTION
        "Entry for the cucsSysdebugTechSupportFsmTaskTable table."
    INDEX { cucsSysdebugTechSupportFsmTaskInstanceId }
    ::= { cucsSysdebugTechSupportFsmTaskTable 1 }

CucsSysdebugTechSupportFsmTaskEntry ::= SEQUENCE {
    cucsSysdebugTechSupportFsmTaskInstanceId                         CucsManagedObjectId,
    cucsSysdebugTechSupportFsmTaskDn                                 CucsManagedObjectDn,
    cucsSysdebugTechSupportFsmTaskRn                                 SnmpAdminString,
    cucsSysdebugTechSupportFsmTaskCompletion                         CucsFsmCompletion,
    cucsSysdebugTechSupportFsmTaskFlags                              CucsFsmFlags,
    cucsSysdebugTechSupportFsmTaskItem                               CucsSysdebugTechSupportFsmTaskItem,
    cucsSysdebugTechSupportFsmTaskSeqId                              Gauge32
}

cucsSysdebugTechSupportFsmTaskInstanceId OBJECT-TYPE
    SYNTAX       CucsManagedObjectId
    MAX-ACCESS   not-accessible
    STATUS       current
    DESCRIPTION
        "Instance identifier of the managed object."
    ::= { cucsSysdebugTechSupportFsmTaskEntry 1 }

cucsSysdebugTechSupportFsmTaskDn OBJECT-TYPE
    SYNTAX       CucsManagedObjectDn
    MAX-ACCESS   read-only
    STATUS       current
    DESCRIPTION
        "Cisco UCS sysdebug:TechSupportFsmTask:dn managed object property"
    ::= { cucsSysdebugTechSupportFsmTaskEntry 2 }

cucsSysdebugTechSupportFsmTaskRn OBJECT-TYPE
    SYNTAX       SnmpAdminString
    MAX-ACCESS   read-only
    STATUS       current
    DESCRIPTION
        "Cisco UCS sysdebug:TechSupportFsmTask:rn managed object property"
    ::= { cucsSysdebugTechSupportFsmTaskEntry 3 }

cucsSysdebugTechSupportFsmTaskCompletion OBJECT-TYPE
    SYNTAX       CucsFsmCompletion
    MAX-ACCESS   read-only
    STATUS       current
    DESCRIPTION
        "Cisco UCS sysdebug:TechSupportFsmTask:completion
        managed object property"
    ::= { cucsSysdebugTechSupportFsmTaskEntry 4 }

cucsSysdebugTechSupportFsmTaskFlags OBJECT-TYPE
    SYNTAX       CucsFsmFlags
    MAX-ACCESS   read-only
    STATUS       current
    DESCRIPTION
        "Cisco UCS sysdebug:TechSupportFsmTask:flags managed
        object property"
    ::= { cucsSysdebugTechSupportFsmTaskEntry 5 }

cucsSysdebugTechSupportFsmTaskItem OBJECT-TYPE
    SYNTAX       CucsSysdebugTechSupportFsmTaskItem
    MAX-ACCESS   read-only
    STATUS       current
    DESCRIPTION
        "Cisco UCS sysdebug:TechSupportFsmTask:item managed
        object property"
    ::= { cucsSysdebugTechSupportFsmTaskEntry 6 }

cucsSysdebugTechSupportFsmTaskSeqId OBJECT-TYPE
    SYNTAX       Gauge32
    MAX-ACCESS   read-only
    STATUS       current
    DESCRIPTION
        "Cisco UCS sysdebug:TechSupportFsmTask:seqId managed
        object property"
    ::= { cucsSysdebugTechSupportFsmTaskEntry 7 }

END
