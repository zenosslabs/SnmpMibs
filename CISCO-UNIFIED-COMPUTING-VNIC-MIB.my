-- *********************************************************************
-- CISCO-UNIFIED-COMPUTING-VNIC-MIB.my
-- 
-- MIB representation of the Cisco Unified Computing System
-- VNIC management information model package
-- 
-- Created September 2011 by Charles Bullis
-- 
-- Copyright (c) 2005-2011 Cisco Systems, Inc. All rights reserved.
-- 
-- *********************************************************************

CISCO-UNIFIED-COMPUTING-VNIC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsConditionRemoteInvRslt,
    CucsDpsecForgedTransmit,
    CucsFsmCompletion,
    CucsFsmFlags,
    CucsLsConfigState,
    CucsNetworkSwitchId,
    CucsNwctrlAdminState,
    CucsNwctrlLinkFailAction,
    CucsVmMgmtPlane,
    CucsVnicAEtherIfType,
    CucsVnicAFcIfType,
    CucsVnicAIpcIfType,
    CucsVnicAScsiIfType,
    CucsVnicConnectionOwner,
    CucsVnicConnectionType,
    CucsVnicDefBehType,
    CucsVnicDefaultAction,
    CucsVnicDynamicConReqProtection,
    CucsVnicEtherBaseSwitchId,
    CucsVnicEtherType,
    CucsVnicExternalMgmtIPMode,
    CucsVnicFcBasePersBind,
    CucsVnicFcBaseType,
    CucsVnicHostNwIOPerfPref,
    CucsVnicIPv4DnsPref,
    CucsVnicIScsiIfDefType,
    CucsVnicIfOperState,
    CucsVnicInstantiation,
    CucsVnicIpcType,
    CucsVnicL2IfSwitchId,
    CucsVnicLanConnTemplSwitchId,
    CucsVnicLunId,
    CucsVnicProfileSetFsmTaskItem,
    CucsVnicSanConnTemplTarget,
    CucsVnicScsiType,
    CucsVnicTemplateTarget,
    CucsVnicTemplateType,
    CucsVnicVnicBootDev
        FROM CISCO-UNIFIED-COMPUTING-TC-MIB;

cucsVnicObjects MODULE-IDENTITY
    LAST-UPDATED    "201109150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        VNIC management information model package"
    ::= { ciscoUnifiedComputingMIBObjects 53 }

cucsVnicBootIpPolicyTable OBJECT-TYPE
    SYNTAX           SEQUENCE OF CucsVnicBootIpPolicyEntry
    MAX-ACCESS       not-accessible
    STATUS           current
    DESCRIPTION
        "Cisco UCS vnic:BootIpPolicy managed object table"
    ::= { cucsVnicObjects 35 }

cucsVnicBootIpPolicyEntry OBJECT-TYPE
    SYNTAX           CucsVnicBootIpPolicyEntry
    MAX-ACCESS       not-accessible
    STATUS           current
    DESCRIPTION
        "Entry for the cucsVnicBootIpPolicyTable table."
    INDEX { cucsVnicBootIpPolicyInstanceId }
    ::= { cucsVnicBootIpPolicyTable 1 }

CucsVnicBootIpPolicyEntry ::= SEQUENCE {
    cucsVnicBootIpPolicyInstanceId                                   CucsManagedObjectId,
    cucsVnicBootIpPolicyDn                                           CucsManagedObjectDn,
    cucsVnicBootIpPolicyRn                                           SnmpAdminString,
    cucsVnicBootIpPolicyDescr                                        SnmpAdminString,
    cucsVnicBootIpPolicyIntId                                        SnmpAdminString,
    cucsVnicBootIpPolicyName                                         SnmpAdminString,
    cucsVnicBootIpPolicyPoolName                                     SnmpAdminString
}

cucsVnicBootIpPolicyInstanceId OBJECT-TYPE
    SYNTAX       CucsManagedObjectId
    MAX-ACCESS   not-accessible
    STATUS       current
    DESCRIPTION
        "Instance identifier of the managed object."
    ::= { cucsVnicBootIpPolicyEntry 1 }

cucsVnicBootIpPolicyDn OBJECT-TYPE
    SYNTAX       CucsManagedObjectDn
    MAX-ACCESS   read-only
    STATUS       current
    DESCRIPTION
        "Cisco UCS vnic:BootIpPolicy:dn managed object property"
    ::= { cucsVnicBootIpPolicyEntry 2 }

cucsVnicBootIpPolicyRn OBJECT-TYPE
    SYNTAX       SnmpAdminString
    MAX-ACCESS   read-only
    STATUS       current
    DESCRIPTION
        "Cisco UCS vnic:BootIpPolicy:rn managed object property"
    ::= { cucsVnicBootIpPolicyEntry 3 }

cucsVnicBootIpPolicyDescr OBJECT-TYPE
    SYNTAX       SnmpAdminString
    MAX-ACCESS   read-only
    STATUS       current
    DESCRIPTION
        "Cisco UCS vnic:BootIpPolicy:descr managed object property"
    ::= { cucsVnicBootIpPolicyEntry 4 }

cucsVnicBootIpPolicyIntId OBJECT-TYPE
    SYNTAX       SnmpAdminString
    MAX-ACCESS   read-only
    STATUS       current
    DESCRIPTION
        "Cisco UCS vnic:BootIpPolicy:intId managed object property"
    ::= { cucsVnicBootIpPolicyEntry 5 }

cucsVnicBootIpPolicyName OBJECT-TYPE
    SYNTAX       SnmpAdminString
    MAX-ACCESS   read-only
    STATUS       current
    DESCRIPTION
        "Cisco UCS vnic:BootIpPolicy:name managed object property"
    ::= { cucsVnicBootIpPolicyEntry 6 }

cucsVnicBootIpPolicyPoolName OBJECT-TYPE
    SYNTAX       SnmpAdminString
    MAX-ACCESS   read-only
    STATUS       current
    DESCRIPTION
        "Cisco UCS vnic:BootIpPolicy:poolName managed object property"
    ::= { cucsVnicBootIpPolicyEntry 7 }

cucsVnicBootTargetTable OBJECT-TYPE
    SYNTAX           SEQUENCE OF CucsVnicBootTargetEntry
    MAX-ACCESS       not-accessible
    STATUS           current
    DESCRIPTION
        "Cisco UCS vnic:BootTarget managed object table"
    ::= { cucsVnicObjects 1 }

cucsVnicBootTargetEntry OBJECT-TYPE
    SYNTAX           CucsVnicBootTargetEntry
    MAX-ACCESS       not-accessible
    STATUS           current
    DESCRIPTION
        "Entry for the cucsVnicBootTargetTable table."
    INDEX { cucsVnicBootTargetInstanceId }
    ::= { cucsVnicBootTargetTable 1 }

CucsVnicBootTargetEntry ::= SEQUENCE {
    cucsVnicBootTargetInstanceId                                     CucsManagedObjectId,
    cucsVnicBootTargetDn                                             CucsManagedObjectDn,
    cucsVnicBootTargetRn                                             SnmpAdminString,
    cucsVnicBootTargetLun                                            SnmpAdminString,
    cucsVnicBootTargetWwn                                            Unsigned64
}

cucsVnicBootTargetInstanceId OBJECT-TYPE
    SYNTAX       CucsManagedObjectId
    MAX-ACCESS   not-accessible
    STATUS       current
    DESCRIPTION
        "Instance identifier of the managed object."
    ::= { cucsVnicBootTargetEntry 1 }

cucsVnicBootTargetDn OBJECT-TYPE
    SYNTAX       CucsManagedObjectDn
    MAX-ACCESS   read-only
    STATUS       current
    DESCRIPTION
        "Cisco UCS vnic:BootTarget:dn managed object property"
    ::= { cucsVnicBootTargetEntry 2 }

cucsVnicBootTargetRn OBJECT-TYPE
    SYNTAX       SnmpAdminString
    MAX-ACCESS   read-only
    STATUS       current
    DESCRIPTION
        "Cisco UCS vnic:BootTarget:rn managed object property"
    ::= { cucsVnicBootTargetEntry 3 }

cucsVnicBootTargetLun OBJECT-TYPE
    SYNTAX       SnmpAdminString
    MAX-ACCESS   read-only
    STATUS       current
    DESCRIPTION
        "Cisco UCS vnic:BootTarget:lun managed object property"
    ::= { cucsVnicBootTargetEntry 4 }

cucsVnicBootTargetWwn OBJECT-TYPE
    SYNTAX       Unsigned64
    MAX-ACCESS   read-only
    STATUS       current
    DESCRIPTION
        "Cisco UCS vnic:BootTarget:wwn managed object property"
    ::= { cucsVnicBootTargetEntry 5 }

cucsVnicDefBehTable OBJECT-TYPE
    SYNTAX           SEQUENCE OF CucsVnicDefBehEntry
    MAX-ACCESS       not-accessible
    STATUS           current
    DESCRIPTION
        "Cisco UCS vnic:DefBeh managed object table"
    ::= { cucsVnicObjects 2 }

cucsVnicDefBehEntry OBJECT-TYPE
    SYNTAX           CucsVnicDefBehEntry
    MAX-ACCESS       not-accessible
    STATUS           current
    DESCRIPTION
        "Entry for the cucsVnicDefBehTable table."
    INDEX { cucsVnicDefBehInstanceId }
    ::= { cucsVnicDefBehTable 1 }

CucsVnicDefBehEntry ::= SEQUENCE {
    cucsVnicDefBehInstanceId                                         CucsManagedObjectId,
    cucsVnicDefBehDn                                                 CucsManagedObjectDn,
    cucsVnicDefBehRn                                                 SnmpAdminString,
    cucsVnicDefBehAction                                             CucsVnicDefaultAction,
    cucsVnicDefBehNwTemplName                                        SnmpAdminString,
    cucsVnicDefBehType                                               CucsVnicDefBehType
}

cucsVnicDefBehInstanceId OBJECT-TYPE
    SYNTAX       CucsManagedObjectId
    MAX-ACCESS   not-accessible
    STATUS       current
    DESCRIPTION
        "Instance identifier of the managed object."
    ::= { cucsVnicDefBehEntry 1 }

cucsVnicDefBehDn OBJECT-TYPE
    SYNTAX       CucsManagedObjectDn
    MAX-ACCESS   read-only
    STATUS       current
    DESCRIPTION
        "Cisco UCS vnic:DefBeh:dn managed object property"
    ::= { cucsVnicDefBehEntry 2 }

cucsVnicDefBehRn OBJECT-TYPE
    SYNTAX       SnmpAdminString
    MAX-ACCESS   read-only
    STATUS       current
    DESCRIPTION
        "Cisco UCS vnic:DefBeh:rn managed object property"
    ::= { cucsVnicDefBehEntry 3 }

cucsVnicDefBehAction OBJECT-TYPE
    SYNTAX       CucsVnicDefaultAction
    MAX-ACCESS   read-only
    STATUS       current
    DESCRIPTION
        "Cisco UCS vnic:DefBeh:action managed object property"
    ::= { cucsVnicDefBehEntry 4 }

cucsVnicDefBehNwTemplName OBJECT-TYPE
    SYNTAX       SnmpAdminString
    MAX-ACCESS   read-only
    STATUS       current
    DESCRIPTION
        "Cisco UCS vnic:DefBeh:nwTemplName managed object property"
    ::= { cucsVnicDefBehEntry 5 }

cucsVnicDefBehType OBJECT-TYPE
    SYNTAX       CucsVnicDefBehType
    MAX-ACCESS   read-only
    STATUS       current
    DESCRIPTION
        "Cisco UCS vnic:DefBeh:type managed object property"
    ::= { cucsVnicDefBehEntry 6 }

cucsVnicDynamicConTable OBJECT-TYPE
    SYNTAX           SEQUENCE OF CucsVnicDynamicConEntry
    MAX-ACCESS       not-accessible
    STATUS           current
    DESCRIPTION
        "Cisco UCS vnic:DynamicCon managed object table"
    ::= { cucsVnicObjects 3 }

cucsVnicDynamicConEntry OBJECT-TYPE
    SYNTAX           CucsVnicDynamicConEntry
    MAX-ACCESS       not-accessible
    STATUS           current
    DESCRIPTION
        "Entry for the cucsVnicDynamicConTable table."
    INDEX { cucsVnicDynamicConInstanceId }
    ::= { cucsVnicDynamicConTable 1 }

CucsVnicDynamicConEntry ::= SEQUENCE {
    cucsVnicDynamicConInstanceId                                     CucsManagedObjectId,
    cucsVnicDynamicConDn                                             CucsManagedObjectDn,
    cucsVnicDynamicConRn                                             SnmpAdminString,
    cucsVnicDynamicConAdaptorProfileName                             SnmpAdminString,
    cucsVnicDynamicConDescr                                          SnmpAdminString,
    cucsVnicDynamicConDynamicEth                                     Gauge32,
    cucsVnicDynamicConIntId                                          SnmpAdminString,
    cucsVnicDynamicConMtu                                            Gauge32,
    cucsVnicDynamicConName                                           SnmpAdminString,
    cucsVnicDynamicConNamingPrefix                                   SnmpAdminString,
    cucsVnicDynamicConProtection                                     CucsVnicDynamicConReqProtection
}

cucsVnicDynamicConInstanceId OBJECT-TYPE
    SYNTAX       CucsManagedObjectId
    MAX-ACCESS   not-accessible
    STATUS       current
    DESCRIPTION
        "Instance identifier of the managed object."
    ::= { cucsVnicDynamicConEntry 1 }

cucsVnicDynamicConDn OBJECT-TYPE
    SYNTAX       CucsManagedObjectDn
    MAX-ACCESS   read-only
    STATUS       current
    DESCRIPTION
        "Cisco UCS vnic:DynamicCon:dn managed object property"
    ::= { cucsVnicDynamicConEntry 2 }

cucsVnicDynamicConRn OBJECT-TYPE
    SYNTAX       SnmpAdminString
    MAX-ACCESS   read-only
    STATUS       current
    DESCRIPTION
        "Cisco UCS vnic:DynamicCon:rn managed object property"
    ::= { cucsVnicDynamicConEntry 3 }

cucsVnicDynamicConAdaptorProfileName OBJECT-TYPE
    SYNTAX       SnmpAdminString
    MAX-ACCESS   read-only
    STATUS       current
    DESCRIPTION
        "Cisco UCS vnic:DynamicCon:adaptorProfileName managed
        object property"
    ::= { cucsVnicDynamicConEntry 4 }

cucsVnicDynamicConDescr OBJECT-TYPE
    SYNTAX       SnmpAdminString
    MAX-ACCESS   read-only
    STATUS       current
    DESCRIPTION
        "Cisco UCS vnic:DynamicCon:descr managed object property"
    ::= { cucsVnicDynamicConEntry 5 }

cucsVnicDynamicConDynamicEth OBJECT-TYPE
    SYNTAX       Gauge32
    MAX-ACCESS   read-only
    STATUS       current
    DESCRIPTION
        "Cisco UCS vnic:DynamicCon:dynamicEth managed object property"
    ::= { cucsVnicDynamicConEntry 6 }

cucsVnicDynamicConIntId OBJECT-TYPE
    SYNTAX       SnmpAdminString
    MAX-ACCESS   read-only
    STATUS       current
    DESCRIPTION
        "Cisco UCS vnic:DynamicCon:intId managed object property"
    ::= { cucsVnicDynamicConEntry 7 }

cucsVnicDynamicConMtu OBJECT-TYPE
    SYNTAX       Gauge32
    MAX-ACCESS   read-only
    STATUS       current
    DESCRIPTION
        "Cisco UCS vnic:DynamicCon:mtu managed object property"
    ::= { cucsVnicDynamicConEntry 8 }

cucsVnicDynamicConName OBJECT-TYPE
    SYNTAX       SnmpAdminString
    MAX-ACCESS   read-only
    STATUS       current
    DESCRIPTION
        "Cisco UCS vnic:DynamicCon:name managed object property"
    ::= { cucsVnicDynamicConEntry 9 }

cucsVnicDynamicConNamingPrefix OBJECT-TYPE
    SYNTAX       SnmpAdminString
    MAX-ACCESS   read-only
    STATUS       current
    DESCRIPTION
        "Cisco UCS vnic:DynamicCon:namingPrefix managed object property"
    ::= { cucsVnicDynamicConEntry 10 }

cucsVnicDynamicConProtection OBJECT-TYPE
    SYNTAX       CucsVnicDynamicConReqProtection
    MAX-ACCESS   read-only
    STATUS       current
    DESCRIPTION
        "Cisco UCS vnic:DynamicCon:protection managed object property"
    ::= { cucsVnicDynamicConEntry 11 }

cucsVnicDynamicConPolicyTable OBJECT-TYPE
    SYNTAX           SEQUENCE OF CucsVnicDynamicConPolicyEntry
    MAX-ACCESS       not-accessible
    STATUS           current
    DESCRIPTION
        "Cisco UCS vnic:DynamicConPolicy managed object table"
    ::= { cucsVnicObjects 4 }

cucsVnicDynamicConPolicyEntry OBJECT-TYPE
    SYNTAX           CucsVnicDynamicConPolicyEntry
    MAX-ACCESS       not-accessible
    STATUS           current
    DESCRIPTION
        "Entry for the cucsVnicDynamicConPolicyTable table."
    INDEX { cucsVnicDynamicConPolicyInstanceId }
    ::= { cucsVnicDynamicConPolicyTable 1 }

CucsVnicDynamicConPolicyEntry ::= SEQUENCE {
    cucsVnicDynamicConPolicyInstanceId                               CucsManagedObjectId,
    cucsVnicDynamicConPolicyDn                                       CucsManagedObjectDn,
    cucsVnicDynamicConPolicyRn                                       SnmpAdminString,
    cucsVnicDynamicConPolicyAdaptorProfileName                       SnmpAdminString,
    cucsVnicDynamicConPolicyDescr                                    SnmpAdminString,
    cucsVnicDynamicConPolicyDynamicEth                               Gauge32,
    cucsVnicDynamicConPolicyIntId                                    SnmpAdminString,
    cucsVnicDynamicConPolicyMtu                                      Gauge32,
    cucsVnicDynamicConPolicyName                                     SnmpAdminString,
    cucsVnicDynamicConPolicyNamingPrefix                             SnmpAdminString,
    cucsVnicDynamicConPolicyProtection                               CucsVnicDynamicConReqProtection
}

cucsVnicDynamicConPolicyInstanceId OBJECT-TYPE
    SYNTAX       CucsManagedObjectId
    MAX-ACCESS   not-accessible
    STATUS       current
    DESCRIPTION
        "Instance identifier of the managed object."
    ::= { cucsVnicDynamicConPolicyEntry 1 }

cucsVnicDynamicConPolicyDn OBJECT-TYPE
    SYNTAX       CucsManagedObjectDn
    MAX-ACCESS   read-only
    STATUS       current
    DESCRIPTION
        "Cisco UCS vnic:DynamicConPolicy:dn managed object property"
    ::= { cucsVnicDynamicConPolicyEntry 2 }

cucsVnicDynamicConPolicyRn OBJECT-TYPE
    SYNTAX       SnmpAdminString
    MAX-ACCESS   read-only
    STATUS       current
    DESCRIPTION
        "Cisco UCS vnic:DynamicConPolicy:rn managed object property"
    ::= { cucsVnicDynamicConPolicyEntry 3 }

cucsVnicDynamicConPolicyAdaptorProfileName OBJECT-TYPE
    SYNTAX       SnmpAdminString
    MAX-ACCESS   read-only
    STATUS       current
    DESCRIPTION
        "Cisco UCS vnic:DynamicConPolicy:adaptorProfileName
        managed object property"
    ::= { cucsVnicDynamicConPolicyEntry 4 }

cucsVnicDynamicConPolicyDescr OBJECT-TYPE
    SYNTAX       SnmpAdminString
    MAX-ACCESS   read-only
    STATUS       current
    DESCRIPTION
        "Cisco UCS vnic:DynamicConPolicy:descr managed object property"
    ::= { cucsVnicDynamicConPolicyEntry 5 }

cucsVnicDynamicConPolicyDynamicEth OBJECT-TYPE
    SYNTAX       Gauge32
    MAX-ACCESS   read-only
    STATUS       current
    DESCRIPTION
        "Cisco UCS vnic:DynamicConPolicy:dynamicEth managed
        object property"
    ::= { cucsVnicDynamicConPolicyEntry 6 }

cucsVnicDynamicConPolicyIntId OBJECT-TYPE
    SYNTAX       SnmpAdminString
    MAX-ACCESS   read-only
    STATUS       current
    DESCRIPTION
        "Cisco UCS vnic:DynamicConPolicy:intId managed object property"
    ::= { cucsVnicDynamicConPolicyEntry 7 }

cucsVnicDynamicConPolicyMtu OBJECT-TYPE
    SYNTAX       Gauge32
    MAX-ACCESS   read-only
    STATUS       current
    DESCRIPTION
        "Cisco UCS vnic:DynamicConPolicy:mtu managed object property"
    ::= { cucsVnicDynamicConPolicyEntry 8 }

cucsVnicDynamicConPolicyName OBJECT-TYPE
    SYNTAX       SnmpAdminString
    MAX-ACCESS   read-only
    STATUS       current
    DESCRIPTION
        "Cisco UCS vnic:DynamicConPolicy:name managed object property"
    ::= { cucsVnicDynamicConPolicyEntry 9 }

cucsVnicDynamicConPolicyNamingPrefix OBJECT-TYPE
    SYNTAX       SnmpAdminString
    MAX-ACCESS   read-only
    STATUS       current
    DESCRIPTION
        "Cisco UCS vnic:DynamicConPolicy:namingPrefix managed
        object property"
    ::= { cucsVnicDynamicConPolicyEntry 10 }

cucsVnicDynamicConPolicyProtection OBJECT-TYPE
    SYNTAX       CucsVnicDynamicConReqProtection
    MAX-ACCESS   read-only
    STATUS       current
    DESCRIPTION
        "Cisco UCS vnic:DynamicConPolicy:protection managed
        object property"
    ::= { cucsVnicDynamicConPolicyEntry 11 }

cucsVnicDynamicIdUniverseTable OBJECT-TYPE
    SYNTAX           SEQUENCE OF CucsVnicDynamicIdUniverseEntry
    MAX-ACCESS       not-accessible
    STATUS           current
    DESCRIPTION
        "Cisco UCS vnic:DynamicIdUniverse managed object table"
    ::= { cucsVnicObjects 5 }

cucsVnicDynamicIdUniverseEntry OBJECT-TYPE
    SYNTAX           CucsVnicDynamicIdUniverseEntry
    MAX-ACCESS       not-accessible
    STATUS           current
    DESCRIPTION
        "Entry for the cucsVnicDynamicIdUniverseTable table."
    INDEX { cucsVnicDynamicIdUniverseInstanceId }
    ::= { cucsVnicDynamicIdUniverseTable 1 }

CucsVnicDynamicIdUniverseEntry ::= SEQUENCE {
    cucsVnicDynamicIdUniverseInstanceId                              CucsManagedObjectId,
    cucsVnicDynamicIdUniverseDn                                      CucsManagedObjectDn,
    cucsVnicDynamicIdUniverseRn                                      SnmpAdminString,
    cucsVnicDynamicIdUniverseDescr                                   SnmpAdminString,
    cucsVnicDynamicIdUniverseIntId                                   SnmpAdminString,
    cucsVnicDynamicIdUniverseName                                    SnmpAdminString
}

cucsVnicDynamicIdUniverseInstanceId OBJECT-TYPE
    SYNTAX       CucsManagedObjectId
    MAX-ACCESS   not-accessible
    STATUS       current
    DESCRIPTION
        "Instance identifier of the managed object."
    ::= { cucsVnicDynamicIdUniverseEntry 1 }

cucsVnicDynamicIdUniverseDn OBJECT-TYPE
    SYNTAX       CucsManagedObjectDn
    MAX-ACCESS   read-only
    STATUS       current
    DESCRIPTION
        "Cisco UCS vnic:DynamicIdUniverse:dn managed object property"
    ::= { cucsVnicDynamicIdUniverseEntry 2 }

cucsVnicDynamicIdUniverseRn OBJECT-TYPE
    SYNTAX       SnmpAdminString
    MAX-ACCESS   read-only
    STATUS       current
    DESCRIPTION
        "Cisco UCS vnic:DynamicIdUniverse:rn managed object property"
    ::= { cucsVnicDynamicIdUniverseEntry 3 }

cucsVnicDynamicIdUniverseDescr OBJECT-TYPE
    SYNTAX       SnmpAdminString
    MAX-ACCESS   read-only
    STATUS       current
    DESCRIPTION
        "Cisco UCS vnic:DynamicIdUniverse:descr managed object property"
    ::= { cucsVnicDynamicIdUniverseEntry 4 }

cucsVnicDynamicIdUniverseIntId OBJECT-TYPE
    SYNTAX       SnmpAdminString
    MAX-ACCESS   read-only
    STATUS       current
    DESCRIPTION
        "Cisco UCS vnic:DynamicIdUniverse:intId managed object property"
    ::= { cucsVnicDynamicIdUniverseEntry 5 }

cucsVnicDynamicIdUniverseName OBJECT-TYPE
    SYNTAX       SnmpAdminString
    MAX-ACCESS   read-only
    STATUS       current
    DESCRIPTION
        "Cisco UCS vnic:DynamicIdUniverse:name managed object property"
    ::= { cucsVnicDynamicIdUniverseEntry 6 }

cucsVnicDynamicProviderTable OBJECT-TYPE
    SYNTAX           SEQUENCE OF CucsVnicDynamicProviderEntry
    MAX-ACCESS       not-accessible
    STATUS           current
    DESCRIPTION
        "Cisco UCS vnic:DynamicProvider managed object table"
    ::= { cucsVnicObjects 6 }

cucsVnicDynamicProviderEntry OBJECT-TYPE
    SYNTAX           CucsVnicDynamicProviderEntry
    MAX-ACCESS       not-accessible
    STATUS           current
    DESCRIPTION
        "Entry for the cucsVnicDynamicProviderTable table."
    INDEX { cucsVnicDynamicProviderInstanceId }
    ::= { cucsVnicDynamicProviderTable 1 }

CucsVnicDynamicProviderEntry ::= SEQUENCE {
    cucsVnicDynamicProviderInstanceId                                CucsManagedObjectId,
    cucsVnicDynamicProviderDn                                        CucsManagedObjectDn,
    cucsVnicDynamicProviderRn                                        SnmpAdminString,
    cucsVnicDynamicProviderName                                      SnmpAdminString
}

cucsVnicDynamicProviderInstanceId OBJECT-TYPE
    SYNTAX       CucsManagedObjectId
    MAX-ACCESS   not-accessible
    STATUS       current
    DESCRIPTION
        "Instance identifier of the managed object."
    ::= { cucsVnicDynamicProviderEntry 1 }

cucsVnicDynamicProviderDn OBJECT-TYPE
    SYNTAX       CucsManagedObjectDn
    MAX-ACCESS   read-only
    STATUS       current
    DESCRIPTION
        "Cisco UCS vnic:DynamicProvider:dn managed object property"
    ::= { cucsVnicDynamicProviderEntry 2 }

cucsVnicDynamicProviderRn OBJECT-TYPE
    SYNTAX       SnmpAdminString
    MAX-ACCESS   read-only
    STATUS       current
    DESCRIPTION
        "Cisco UCS vnic:DynamicProvider:rn managed object property"
    ::= { cucsVnicDynamicProviderEntry 3 }

cucsVnicDynamicProviderName OBJECT-TYPE
    SYNTAX       SnmpAdminString
    MAX-ACCESS   read-only
    STATUS       current
    DESCRIPTION
        "Cisco UCS vnic:DynamicProvider:name managed object property"
    ::= { cucsVnicDynamicProviderEntry 4 }

cucsVnicDynamicProviderEpTable OBJECT-TYPE
    SYNTAX           SEQUENCE OF CucsVnicDynamicProviderEpEntry
    MAX-ACCESS       not-accessible
    STATUS           current
    DESCRIPTION
        "Cisco UCS vnic:DynamicProviderEp managed object table"
    ::= { cucsVnicObjects 7 }

cucsVnicDynamicProviderEpEntry OBJECT-TYPE
    SYNTAX           CucsVnicDynamicProviderEpEntry
    MAX-ACCESS       not-accessible
    STATUS           current
    DESCRIPTION
        "Entry for the cucsVnicDynamicProviderEpTable table."
    INDEX { cucsVnicDynamicProviderEpInstanceId }
    ::= { cucsVnicDynamicProviderEpTable 1 }

CucsVnicDynamicProviderEpEntry ::= SEQUENCE {
    cucsVnicDynamicProviderEpInstanceId                              CucsManagedObjectId,
    cucsVnicDynamicProviderEpDn                                      CucsManagedObjectDn,
    cucsVnicDynamicProviderEpRn                                      SnmpAdminString,
    cucsVnicDynamicProviderEpChassisId                               Gauge32,
    cucsVnicDynamicProviderEpPortId                                  Gauge32,
    cucsVnicDynamicProviderEpSlotId                                  Gauge32,
    cucsVnicDynamicProviderEpSwitchId                                CucsNetworkSwitchId
}

cucsVnicDynamicProviderEpInstanceId OBJECT-TYPE
    SYNTAX       CucsManagedObjectId
    MAX-ACCESS   not-accessible
    STATUS       current
    DESCRIPTION
        "Instance identifier of the managed object."
    ::= { cucsVnicDynamicProviderEpEntry 1 }

cucsVnicDynamicProviderEpDn OBJECT-TYPE
    SYNTAX       CucsManagedObjectDn
    MAX-ACCESS   read-only
    STATUS       current
    DESCRIPTION
        "Cisco UCS vnic:DynamicProviderEp:dn managed object property"
    ::= { cucsVnicDynamicProviderEpEntry 2 }

cucsVnicDynamicProviderEpRn OBJECT-TYPE
    SYNTAX       SnmpAdminString
    MAX-ACCESS   read-only
    STATUS       current
    DESCRIPTION
        "Cisco UCS vnic:DynamicProviderEp:rn managed object property"
    ::= { cucsVnicDynamicProviderEpEntry 3 }

cucsVnicDynamicProviderEpChassisId OBJECT-TYPE
    SYNTAX       Gauge32
    MAX-ACCESS   read-only
    STATUS       current
    DESCRIPTION
        "Cisco UCS vnic:DynamicProviderEp:chassisId managed
        object property"
    ::= { cucsVnicDynamicProviderEpEntry 4 }

cucsVnicDynamicProviderEpPortId OBJECT-TYPE
    SYNTAX       Gauge32
    MAX-ACCESS   read-only
    STATUS       current
    DESCRIPTION
        "Cisco UCS vnic:DynamicProviderEp:portId managed object property"
    ::= { cucsVnicDynamicProviderEpEntry 5 }

cucsVnicDynamicProviderEpSlotId OBJECT-TYPE
    SYNTAX       Gauge32
    MAX-ACCESS   read-only
    STATUS       current
    DESCRIPTION
        "Cisco UCS vnic:DynamicProviderEp:slotId managed object property"
    ::= { cucsVnicDynamicProviderEpEntry 6 }

cucsVnicDynamicProviderEpSwitchId OBJECT-TYPE
    SYNTAX       CucsNetworkSwitchId
    MAX-ACCESS   read-only
    STATUS       current
    DESCRIPTION
        "Cisco UCS vnic:DynamicProviderEp:switchId managed
        object property"
    ::= { cucsVnicDynamicProviderEpEntry 7 }

cucsVnicEthLifTable OBJECT-TYPE
    SYNTAX           SEQUENCE OF CucsVnicEthLifEntry
    MAX-ACCESS       not-accessible
    STATUS           current
    DESCRIPTION
        "Cisco UCS vnic:EthLif managed object table"
    ::= { cucsVnicObjects 8 }

cucsVnicEthLifEntry OBJECT-TYPE
    SYNTAX           CucsVnicEthLifEntry
    MAX-ACCESS       not-accessible
    STATUS           current
    DESCRIPTION
        "Entry for the cucsVnicEthLifTable table."
    INDEX { cucsVnicEthLifInstanceId }
    ::= { cucsVnicEthLifTable 1 }

CucsVnicEthLifEntry ::= SEQUENCE {
    cucsVnicEthLifInstanceId                                         CucsManagedObjectId,
    cucsVnicEthLifDn                                                 CucsManagedObjectDn,
    cucsVnicEthLifRn                                                 SnmpAdminString,
    cucsVnicEthLifAddr                                               MacAddress,
    cucsVnicEthLifName                                               SnmpAdminString,
    cucsVnicEthLifNicDn                                              SnmpAdminString,
    cucsVnicEthLifOwner                                              CucsVnicConnectionOwner,
    cucsVnicEthLifSwitchId                                           CucsNetworkSwitchId,
    cucsVnicEthLifType                                               CucsVnicConnectionType,
    cucsVnicEthLifVnicDn                                             SnmpAdminString
}

cucsVnicEthLifInstanceId OBJECT-TYPE
    SYNTAX       CucsManagedObjectId
    MAX-ACCESS   not-accessible
    STATUS       current
    DESCRIPTION
        "Instance identifier of the managed object."
    ::= { cucsVnicEthLifEntry 1 }

cucsVnicEthLifDn OBJECT-TYPE
    SYNTAX       CucsManagedObjectDn
    MAX-ACCESS   read-only
    STATUS       current
    DESCRIPTION
        "Cisco UCS vnic:EthLif:dn managed object property"
    ::= { cucsVnicEthLifEntry 2 }

cucsVnicEthLifRn OBJECT-TYPE
    SYNTAX       SnmpAdminString
    MAX-ACCESS   read-only
    STATUS       current
    DESCRIPTION
        "Cisco UCS vnic:EthLif:rn managed object property"
    ::= { cucsVnicEthLifEntry 3 }

cucsVnicEthLifAddr OBJECT-TYPE
    SYNTAX       MacAddress
    MAX-ACCESS   read-only
    STATUS       current
    DESCRIPTION
        "Cisco UCS vnic:EthLif:addr managed object property"
    ::= { cucsVnicEthLifEntry 4 }

cucsVnicEthLifName OBJECT-TYPE
    SYNTAX       SnmpAdminString
    MAX-ACCESS   read-only
    STATUS       current
    DESCRIPTION
        "Cisco UCS vnic:EthLif:name managed object property"
    ::= { cucsVnicEthLifEntry 5 }

cucsVnicEthLifNicDn OBJECT-TYPE
    SYNTAX       SnmpAdminString
    MAX-ACCESS   read-only
    STATUS       current
    DESCRIPTION
        "Cisco UCS vnic:EthLif:nicDn managed object property"
    ::= { cucsVnicEthLifEntry 6 }

cucsVnicEthLifOwner OBJECT-TYPE
    SYNTAX       CucsVnicConnectionOwner
    MAX-ACCESS   read-only
    STATUS       current
    DESCRIPTION
        "Cisco UCS vnic:EthLif:owner managed object property"
    ::= { cucsVnicEthLifEntry 7 }

cucsVnicEthLifSwitchId OBJECT-TYPE
    SYNTAX       CucsNetworkSwitchId
    MAX-ACCESS   read-only
    STATUS       current
    DESCRIPTION
        "Cisco UCS vnic:EthLif:switchId managed object property"
    ::= { cucsVnicEthLifEntry 8 }

cucsVnicEthLifType OBJECT-TYPE
    SYNTAX       CucsVnicConnectionType
    MAX-ACCESS   read-only
    STATUS       current
    DESCRIPTION
        "Cisco UCS vnic:EthLif:type managed object property"
    ::= { cucsVnicEthLifEntry 9 }

cucsVnicEthLifVnicDn OBJECT-TYPE
    SYNTAX       SnmpAdminString
    MAX-ACCESS   read-only
    STATUS       current
    DESCRIPTION
        "Cisco UCS vnic:EthLif:vnicDn managed object property"
    ::= { cucsVnicEthLifEntry 10 }

cucsVnicEtherTable OBJECT-TYPE
    SYNTAX           SEQUENCE OF CucsVnicEtherEntry
    MAX-ACCESS       not-accessible
    STATUS           current
    DESCRIPTION
        "Cisco UCS vnic:Ether managed object table"
    ::= { cucsVnicObjects 9 }

cucsVnicEtherEntry OBJECT-TYPE
    SYNTAX           CucsVnicEtherEntry
    MAX-ACCESS       not-accessible
    STATUS           current
    DESCRIPTION
        "Entry for the cucsVnicEtherTable table."
    INDEX { cucsVnicEtherInstanceId }
    ::= { cucsVnicEtherTable 1 }

CucsVnicEtherEntry ::= SEQUENCE {
    cucsVnicEtherInstanceId                                          CucsManagedObjectId,
    cucsVnicEtherDn                                                  CucsManagedObjectDn,
    cucsVnicEtherRn                                                  SnmpAdminString,
    cucsVnicEtherAdaptorProfileName                                  SnmpAdminString,
    cucsVnicEtherAddr                                                MacAddress,
    cucsVnicEtherAdminVcon                                           SnmpAdminString,
    cucsVnicEtherBootDev                                             CucsVnicVnicBootDev,
    cucsVnicEtherConfigState                                         CucsLsConfigState,
    cucsVnicEtherEquipmentDn                                         SnmpAdminString,
    cucsVnicEtherFltAggr                                             Unsigned64,
    cucsVnicEtherIdentPoolName                                       SnmpAdminString,
    cucsVnicEtherInstType                                            CucsVnicInstantiation,
    cucsVnicEtherMtu                                                 Gauge32,
    cucsVnicEtherName                                                SnmpAdminString,
    cucsVnicEtherNwCtrlPolicyName                                    SnmpAdminString,
    cucsVnicEtherNwTemplName                                         SnmpAdminString,
    cucsVnicEtherOperAdaptorProfileName                              SnmpAdminString,
    cucsVnicEtherOperIdentPoolName                                   SnmpAdminString,
    cucsVnicEtherOperNwCtrlPolicyName                                SnmpAdminString,
    cucsVnicEtherOperNwTemplName                                     SnmpAdminString,
    cucsVnicEtherOperOrder                                           Gauge32,
    cucsVnicEtherOperQosPolicyName                                   SnmpAdminString,
    cucsVnicEtherOperSpeed                                           Gauge32,
    cucsVnicEtherOperStatsPolicyName                                 SnmpAdminString,
    cucsVnicEtherOperVcon                                            SnmpAdminString,
    cucsVnicEtherOrder                                               Gauge32,
    cucsVnicEtherOwner                                               CucsVnicConnectionOwner,
    cucsVnicEtherPinToGroupName                                      SnmpAdminString,
    cucsVnicEtherQosPolicyName                                       SnmpAdminString,
    cucsVnicEtherStatsPolicyName                                     SnmpAdminString,
    cucsVnicEtherSwitchId                                            CucsVnicEtherBaseSwitchId,
    cucsVnicEtherType                                                CucsVnicEtherType,
    cucsVnicEtherOperPinToGroupName                                  SnmpAdminString
}

cucsVnicEtherInstanceId OBJECT-TYPE
    SYNTAX       CucsManagedObjectId
    MAX-ACCESS   not-accessible
    STATUS       current
    DESCRIPTION
        "Instance identifier of the managed object."
    ::= { cucsVnicEtherEntry 1 }

cucsVnicEtherDn OBJECT-TYPE
    SYNTAX       CucsManagedObjectDn
    MAX-ACCESS   read-only
    STATUS       current
    DESCRIPTION
        "Cisco UCS vnic:Ether:dn managed object property"
    ::= { cucsVnicEtherEntry 2 }

cucsVnicEtherRn OBJECT-TYPE
    SYNTAX       SnmpAdminString
    MAX-ACCESS   read-only
    STATUS       current
    DESCRIPTION
        "Cisco UCS vnic:Ether:rn managed object property"
    ::= { cucsVnicEtherEntry 3 }

cucsVnicEtherAdaptorProfileName OBJECT-TYPE
    SYNTAX       SnmpAdminString
    MAX-ACCESS   read-only
    STATUS       current
    DESCRIPTION
        "Cisco UCS vnic:Ether:adaptorProfileName managed object property"
    ::= { cucsVnicEtherEntry 4 }

cucsVnicEtherAddr OBJECT-TYPE
    SYNTAX       MacAddress
    MAX-ACCESS   read-only
    STATUS       current
    DESCRIPTION
        "Cisco UCS vnic:Ether:addr managed object property"
    ::= { cucsVnicEtherEntry 5 }

cucsVnicEtherAdminVcon OBJECT-TYPE
    SYNTAX       SnmpAdminString
    MAX-ACCESS   read-only
    STATUS       current
    DESCRIPTION
        "Cisco UCS vnic:Ether:adminVcon managed object property"
    ::= { cucsVnicEtherEntry 6 }

cucsVnicEtherBootDev OBJECT-TYPE
    SYNTAX       CucsVnicVnicBootDev
    MAX-ACCESS   read-only
    STATUS       current
    DESCRIPTION
        "Cisco UCS vnic:Ether:bootDev managed object property"
    ::= { cucsVnicEtherEntry 7 }

cucsVnicEtherConfigState OBJECT-TYPE
    SYNTAX       CucsLsConfigState
    MAX-ACCESS   read-only
    STATUS       current
    DESCRIPTION
        "Cisco UCS vnic:Ether:configState managed object property"
    ::= { cucsVnicEtherEntry 8 }

cucsVnicEtherEquipmentDn OBJECT-TYPE
    SYNTAX       SnmpAdminString
    MAX-ACCESS   read-only
    STATUS       current
    DESCRIPTION
        "Cisco UCS vnic:Ether:equipmentDn managed object property"
    ::= { cucsVnicEtherEntry 9 }

cucsVnicEtherFltAggr OBJECT-TYPE
    SYNTAX       Unsigned64
    MAX-ACCESS   read-only
    STATUS       current
    DESCRIPTION
        "Cisco UCS vnic:Ether:fltAggr managed object property"
    ::= { cucsVnicEtherEntry 10 }

cucsVnicEtherIdentPoolName OBJECT-TYPE
    SYNTAX       SnmpAdminString
    MAX-ACCESS   read-only
    STATUS       current
    DESCRIPTION
        "Cisco UCS vnic:Ether:identPoolName managed object property"
    ::= { cucsVnicEtherEntry 11 }

cucsVnicEtherInstType OBJECT-TYPE
    SYNTAX       CucsVnicInstantiation
    MAX-ACCESS   read-only
    STATUS       current
    DESCRIPTION
        "Cisco UCS vnic:Ether:instType managed object property"
    ::= { cucsVnicEtherEntry 12 }

cucsVnicEtherMtu OBJECT-TYPE
    SYNTAX       Gauge32
    MAX-ACCESS   read-only
    STATUS       current
    DESCRIPTION
        "Cisco UCS vnic:Ether:mtu managed object property"
    ::= { cucsVnicEtherEntry 13 }

cucsVnicEtherName OBJECT-TYPE
    SYNTAX       SnmpAdminString
    MAX-ACCESS   read-only
    STATUS       current
    DESCRIPTION
        "Cisco UCS vnic:Ether:name managed object property"
    ::= { cucsVnicEtherEntry 14 }

cucsVnicEtherNwCtrlPolicyName OBJECT-TYPE
    SYNTAX       SnmpAdminString
    MAX-ACCESS   read-only
    STATUS       current
    DESCRIPTION
        "Cisco UCS vnic:Ether:nwCtrlPolicyName managed object property"
    ::= { cucsVnicEtherEntry 15 }

cucsVnicEtherNwTemplName OBJECT-TYPE
    SYNTAX       SnmpAdminString
    MAX-ACCESS   read-only
    STATUS       current
    DESCRIPTION
        "Cisco UCS vnic:Ether:nwTemplName managed object property"
    ::= { cucsVnicEtherEntry 16 }

cucsVnicEtherOperAdaptorProfileName OBJECT-TYPE
    SYNTAX       SnmpAdminString
    MAX-ACCESS   read-only
    STATUS       current
    DESCRIPTION
        "Cisco UCS vnic:Ether:operAdaptorProfileName managed
        object property"
    ::= { cucsVnicEtherEntry 17 }

cucsVnicEtherOperIdentPoolName OBJECT-TYPE
    SYNTAX       SnmpAdminString
    MAX-ACCESS   read-only
    STATUS       current
    DESCRIPTION
        "Cisco UCS vnic:Ether:operIdentPoolName managed object property"
    ::= { cucsVnicEtherEntry 18 }

cucsVnicEtherOperNwCtrlPolicyName OBJECT-TYPE
    SYNTAX       SnmpAdminString
    MAX-ACCESS   read-only
    STATUS       current
    DESCRIPTION
        "Cisco UCS vnic:Ether:operNwCtrlPolicyName managed
        object property"
    ::= { cucsVnicEtherEntry 19 }

cucsVnicEtherOperNwTemplName OBJECT-TYPE
    SYNTAX       SnmpAdminString
    MAX-ACCESS   read-only
    STATUS       current
    DESCRIPTION
        "Cisco UCS vnic:Ether:operNwTemplName managed object property"
    ::= { cucsVnicEtherEntry 20 }

cucsVnicEtherOperOrder OBJECT-TYPE
    SYNTAX       Gauge32
    MAX-ACCESS   read-only
    STATUS       current
    DESCRIPTION
        "Cisco UCS vnic:Ether:operOrder managed object property"
    ::= { cucsVnicEtherEntry 21 }

cucsVnicEtherOperQosPolicyName OBJECT-TYPE
    SYNTAX       SnmpAdminString
    MAX-ACCESS   read-only
    STATUS       current
    DESCRIPTION
        "Cisco UCS vnic:Ether:operQosPolicyName managed object property"
    ::= { cucsVnicEtherEntry 22 }

cucsVnicEtherOperSpeed OBJECT-TYPE
    SYNTAX       Gauge32
    MAX-ACCESS   read-only
    STATUS       current
    DESCRIPTION
        "Cisco UCS vnic:Ether:operSpeed managed object property"
    ::= { cucsVnicEtherEntry 23 }

cucsVnicEtherOperStatsPolicyName OBJECT-TYPE
    SYNTAX       SnmpAdminString
    MAX-ACCESS   read-only
    STATUS       current
    DESCRIPTION
        "Cisco UCS vnic:Ether:operStatsPolicyName managed object property"
    ::= { cucsVnicEtherEntry 24 }

cucsVnicEtherOperVcon OBJECT-TYPE
    SYNTAX       SnmpAdminString
    MAX-ACCESS   read-only
    STATUS       current
    DESCRIPTION
        "Cisco UCS vnic:Ether:operVcon managed object property"
    ::= { cucsVnicEtherEntry 25 }

cucsVnicEtherOrder OBJECT-TYPE
    SYNTAX       Gauge32
    MAX-ACCESS   read-only
    STATUS       current
    DESCRIPTION
        "Cisco UCS vnic:Ether:order managed object property"
    ::= { cucsVnicEtherEntry 26 }

cucsVnicEtherOwner OBJECT-TYPE
    SYNTAX       CucsVnicConnectionOwner
    MAX-ACCESS   read-only
    STATUS       current
    DESCRIPTION
        "Cisco UCS vnic:Ether:owner managed object property"
    ::= { cucsVnicEtherEntry 27 }

cucsVnicEtherPinToGroupName OBJECT-TYPE
    SYNTAX       SnmpAdminString
    MAX-ACCESS   read-only
    STATUS       current
    DESCRIPTION
        "Cisco UCS vnic:Ether:pinToGroupName managed object property"
    ::= { cucsVnicEtherEntry 28 }

cucsVnicEtherQosPolicyName OBJECT-TYPE
    SYNTAX       SnmpAdminString
    MAX-ACCESS   read-only
    STATUS       current
    DESCRIPTION
        "Cisco UCS vnic:Ether:qosPolicyName managed object property"
    ::= { cucsVnicEtherEntry 29 }

cucsVnicEtherStatsPolicyName OBJECT-TYPE
    SYNTAX       SnmpAdminString
    MAX-ACCESS   read-only
    STATUS       current
    DESCRIPTION
        "Cisco UCS vnic:Ether:statsPolicyName managed object property"
    ::= { cucsVnicEtherEntry 30 }

cucsVnicEtherSwitchId OBJECT-TYPE
    SYNTAX       CucsVnicEtherBaseSwitchId
    MAX-ACCESS   read-only
    STATUS       current
    DESCRIPTION
        "Cisco UCS vnic:Ether:switchId managed object property"
    ::= { cucsVnicEtherEntry 31 }

cucsVnicEtherType OBJECT-TYPE
    SYNTAX       CucsVnicEtherType
    MAX-ACCESS   read-only
    STATUS       current
    DESCRIPTION
        "Cisco UCS vnic:Ether:type managed object property"
    ::= { cucsVnicEtherEntry 32 }

cucsVnicEtherOperPinToGroupName OBJECT-TYPE
    SYNTAX       SnmpAdminString
    MAX-ACCESS   read-only
    STATUS       current
    DESCRIPTION
        "Cisco UCS vnic:Ether:operPinToGroupName managed object property"
    ::= { cucsVnicEtherEntry 33 }

cucsVnicEtherIfTable OBJECT-TYPE
    SYNTAX           SEQUENCE OF CucsVnicEtherIfEntry
    MAX-ACCESS       not-accessible
    STATUS           current
    DESCRIPTION
        "Cisco UCS vnic:EtherIf managed object table"
    ::= { cucsVnicObjects 10 }

cucsVnicEtherIfEntry OBJECT-TYPE
    SYNTAX           CucsVnicEtherIfEntry
    MAX-ACCESS       not-accessible
    STATUS           current
    DESCRIPTION
        "Entry for the cucsVnicEtherIfTable table."
    INDEX { cucsVnicEtherIfInstanceId }
    ::= { cucsVnicEtherIfTable 1 }

CucsVnicEtherIfEntry ::= SEQUENCE {
    cucsVnicEtherIfInstanceId                                        CucsManagedObjectId,
    cucsVnicEtherIfDn                                                CucsManagedObjectDn,
    cucsVnicEtherIfRn                                                SnmpAdminString,
    cucsVnicEtherIfAddr                                              MacAddress,
    cucsVnicEtherIfDefaultNet                                        TruthValue,
    cucsVnicEtherIfName                                              SnmpAdminString,
    cucsVnicEtherIfOperState                                         CucsVnicIfOperState,
    cucsVnicEtherIfOwner                                             CucsVnicConnectionOwner,
    cucsVnicEtherIfSwitchId                                          CucsVnicL2IfSwitchId,
    cucsVnicEtherIfType                                              CucsVnicAEtherIfType,
    cucsVnicEtherIfVnet                                              Gauge32,
    cucsVnicEtherIfOperVnetDn                                        SnmpAdminString,
    cucsVnicEtherIfOperVnetName                                      SnmpAdminString
}

cucsVnicEtherIfInstanceId OBJECT-TYPE
    SYNTAX       CucsManagedObjectId
    MAX-ACCESS   not-accessible
    STATUS       current
    DESCRIPTION
        "Instance identifier of the managed object."
    ::= { cucsVnicEtherIfEntry 1 }

cucsVnicEtherIfDn OBJECT-TYPE
    SYNTAX       CucsManagedObjectDn
    MAX-ACCESS   read-only
    STATUS       current
    DESCRIPTION
        "Cisco UCS vnic:EtherIf:dn managed object property"
    ::= { cucsVnicEtherIfEntry 2 }

cucsVnicEtherIfRn OBJECT-TYPE
    SYNTAX       SnmpAdminString
    MAX-ACCESS   read-only
    STATUS       current
    DESCRIPTION
        "Cisco UCS vnic:EtherIf:rn managed object property"
    ::= { cucsVnicEtherIfEntry 3 }

cucsVnicEtherIfAddr OBJECT-TYPE
    SYNTAX       MacAddress
    MAX-ACCESS   read-only
    STATUS       current
    DESCRIPTION
        "Cisco UCS vnic:EtherIf:addr managed object property"
    ::= { cucsVnicEtherIfEntry 4 }

cucsVnicEtherIfDefaultNet OBJECT-TYPE
    SYNTAX       TruthValue
    MAX-ACCESS   read-only
    STATUS       current
    DESCRIPTION
        "Cisco UCS vnic:EtherIf:defaultNet managed object property"
    ::= { cucsVnicEtherIfEntry 5 }

cucsVnicEtherIfName OBJECT-TYPE
    SYNTAX       SnmpAdminString
    MAX-ACCESS   read-only
    STATUS       current
    DESCRIPTION
        "Cisco UCS vnic:EtherIf:name managed object property"
    ::= { cucsVnicEtherIfEntry 6 }

cucsVnicEtherIfOperState OBJECT-TYPE
    SYNTAX       CucsVnicIfOperState
    MAX-ACCESS   read-only
    STATUS       current
    DESCRIPTION
        "Cisco UCS vnic:EtherIf:operState managed object property"
    ::= { cucsVnicEtherIfEntry 7 }

cucsVnicEtherIfOwner OBJECT-TYPE
    SYNTAX       CucsVnicConnectionOwner
    MAX-ACCESS   read-only
    STATUS       current
    DESCRIPTION
        "Cisco UCS vnic:EtherIf:owner managed object property"
    ::= { cucsVnicEtherIfEntry 8 }

cucsVnicEtherIfSwitchId OBJECT-TYPE
    SYNTAX       CucsVnicL2IfSwitchId
    MAX-ACCESS   read-only
    STATUS       current
    DESCRIPTION
        "Cisco UCS vnic:EtherIf:switchId managed object property"
    ::= { cucsVnicEtherIfEntry 9 }

cucsVnicEtherIfType OBJECT-TYPE
    SYNTAX       CucsVnicAEtherIfType
    MAX-ACCESS   read-only
    STATUS       current
    DESCRIPTION
        "Cisco UCS vnic:EtherIf:type managed object property"
    ::= { cucsVnicEtherIfEntry 10 }

cucsVnicEtherIfVnet OBJECT-TYPE
    SYNTAX       Gauge32
    MAX-ACCESS   read-only
    STATUS       current
    DESCRIPTION
        "Cisco UCS vnic:EtherIf:vnet managed object property"
    ::= { cucsVnicEtherIfEntry 11 }

cucsVnicEtherIfOperVnetDn OBJECT-TYPE
    SYNTAX       SnmpAdminString
    MAX-ACCESS   read-only
    STATUS       current
    DESCRIPTION
        "Cisco UCS vnic:EtherIf:operVnetDn managed object property"
    ::= { cucsVnicEtherIfEntry 12 }

cucsVnicEtherIfOperVnetName OBJECT-TYPE
    SYNTAX       SnmpAdminString
    MAX-ACCESS   read-only
    STATUS       current
    DESCRIPTION
        "Cisco UCS vnic:EtherIf:operVnetName managed object property"
    ::= { cucsVnicEtherIfEntry 13 }

cucsVnicFcTable OBJECT-TYPE
    SYNTAX           SEQUENCE OF CucsVnicFcEntry
    MAX-ACCESS       not-accessible
    STATUS           current
    DESCRIPTION
        "Cisco UCS vnic:Fc managed object table"
    ::= { cucsVnicObjects 11 }

cucsVnicFcEntry OBJECT-TYPE
    SYNTAX           CucsVnicFcEntry
    MAX-ACCESS       not-accessible
    STATUS           current
    DESCRIPTION
        "Entry for the cucsVnicFcTable table."
    INDEX { cucsVnicFcInstanceId }
    ::= { cucsVnicFcTable 1 }

CucsVnicFcEntry ::= SEQUENCE {
    cucsVnicFcInstanceId                                             CucsManagedObjectId,
    cucsVnicFcDn                                                     CucsManagedObjectDn,
    cucsVnicFcRn                                                     SnmpAdminString,
    cucsVnicFcAdaptorProfileName                                     SnmpAdminString,
    cucsVnicFcAddr                                                   Unsigned64,
    cucsVnicFcAdminVcon                                              SnmpAdminString,
    cucsVnicFcBootDev                                                CucsVnicVnicBootDev,
    cucsVnicFcConfigState                                            CucsLsConfigState,
    cucsVnicFcEquipmentDn                                            SnmpAdminString,
    cucsVnicFcFltAggr                                                Unsigned64,
    cucsVnicFcIdentPoolName                                          SnmpAdminString,
    cucsVnicFcInstType                                               CucsVnicInstantiation,
    cucsVnicFcMaxDataFieldSize                                       Gauge32,
    cucsVnicFcName                                                   SnmpAdminString,
    cucsVnicFcNdAddr                                                 Unsigned64,
    cucsVnicFcNwTemplName                                            SnmpAdminString,
    cucsVnicFcOperAdaptorProfileName                                 SnmpAdminString,
    cucsVnicFcOperIdentPoolName                                      SnmpAdminString,
    cucsVnicFcOperNwTemplName                                        SnmpAdminString,
    cucsVnicFcOperOrder                                              Gauge32,
    cucsVnicFcOperQosPolicyName                                      SnmpAdminString,
    cucsVnicFcOperSpeed                                              Gauge32,
    cucsVnicFcOperStatsPolicyName                                    SnmpAdminString,
    cucsVnicFcOperVcon                                               SnmpAdminString,
    cucsVnicFcOrder                                                  Gauge32,
    cucsVnicFcOwner                                                  CucsVnicConnectionOwner,
    cucsVnicFcPersBind                                               CucsVnicFcBasePersBind,
    cucsVnicFcPersBindClear                                          TruthValue,
    cucsVnicFcPinToGroupName                                         SnmpAdminString,
    cucsVnicFcQosPolicyName                                          SnmpAdminString,
    cucsVnicFcStatsPolicyName                                        SnmpAdminString,
    cucsVnicFcSwitchId                                               CucsNetworkSwitchId,
    cucsVnicFcType                                                   CucsVnicFcBaseType,
    cucsVnicFcOperPinToGroupName                                     SnmpAdminString
}

cucsVnicFcInstanceId OBJECT-TYPE
    SYNTAX       CucsManagedObjectId
    MAX-ACCESS   not-accessible
    STATUS       current
    DESCRIPTION
        "Instance identifier of the managed object."
    ::= { cucsVnicFcEntry 1 }

cucsVnicFcDn OBJECT-TYPE
    SYNTAX       CucsManagedObjectDn
    MAX-ACCESS   read-only
    STATUS       current
    DESCRIPTION
        "Cisco UCS vnic:Fc:dn managed object property"
    ::= { cucsVnicFcEntry 2 }

cucsVnicFcRn OBJECT-TYPE
    SYNTAX       SnmpAdminString
    MAX-ACCESS   read-only
    STATUS       current
    DESCRIPTION
        "Cisco UCS vnic:Fc:rn managed object property"
    ::= { cucsVnicFcEntry 3 }

cucsVnicFcAdaptorProfileName OBJECT-TYPE
    SYNTAX       SnmpAdminString
    MAX-ACCESS   read-only
    STATUS       current
    DESCRIPTION
        "Cisco UCS vnic:Fc:adaptorProfileName managed object property"
    ::= { cucsVnicFcEntry 4 }

cucsVnicFcAddr OBJECT-TYPE
    SYNTAX       Unsigned64
    MAX-ACCESS   read-only
    STATUS       current
    DESCRIPTION
        "Cisco UCS vnic:Fc:addr managed object property"
    ::= { cucsVnicFcEntry 5 }

cucsVnicFcAdminVcon OBJECT-TYPE
    SYNTAX       SnmpAdminString
    MAX-ACCESS   read-only
    STATUS       current
    DESCRIPTION
        "Cisco UCS vnic:Fc:adminVcon managed object property"
    ::= { cucsVnicFcEntry 6 }

cucsVnicFcBootDev OBJECT-TYPE
    SYNTAX       CucsVnicVnicBootDev
    MAX-ACCESS   read-only
    STATUS       current
    DESCRIPTION
        "Cisco UCS vnic:Fc:bootDev managed object property"
    ::= { cucsVnicFcEntry 7 }

cucsVnicFcConfigState OBJECT-TYPE
    SYNTAX       CucsLsConfigState
    MAX-ACCESS   read-only
    STATUS       current
    DESCRIPTION
        "Cisco UCS vnic:Fc:configState managed object property"
    ::= { cucsVnicFcEntry 8 }

cucsVnicFcEquipmentDn OBJECT-TYPE
    SYNTAX       SnmpAdminString
    MAX-ACCESS   read-only
    STATUS       current
    DESCRIPTION
        "Cisco UCS vnic:Fc:equipmentDn managed object property"
    ::= { cucsVnicFcEntry 9 }

cucsVnicFcFltAggr OBJECT-TYPE
    SYNTAX       Unsigned64
    MAX-ACCESS   read-only
    STATUS       current
    DESCRIPTION
        "Cisco UCS vnic:Fc:fltAggr managed object property"
    ::= { cucsVnicFcEntry 10 }

cucsVnicFcIdentPoolName OBJECT-TYPE
    SYNTAX       SnmpAdminString
    MAX-ACCESS   read-only
    STATUS       current
    DESCRIPTION
        "Cisco UCS vnic:Fc:identPoolName managed object property"
    ::= { cucsVnicFcEntry 11 }

cucsVnicFcInstType OBJECT-TYPE
    SYNTAX       CucsVnicInstantiation
    MAX-ACCESS   read-only
    STATUS       current
    DESCRIPTION
        "Cisco UCS vnic:Fc:instType managed object property"
    ::= { cucsVnicFcEntry 12 }

cucsVnicFcMaxDataFieldSize OBJECT-TYPE
    SYNTAX       Gauge32
    MAX-ACCESS   read-only
    STATUS       current
    DESCRIPTION
        "Cisco UCS vnic:Fc:maxDataFieldSize managed object property"
    ::= { cucsVnicFcEntry 13 }

cucsVnicFcName OBJECT-TYPE
    SYNTAX       SnmpAdminString
    MAX-ACCESS   read-only
    STATUS       current
    DESCRIPTION
        "Cisco UCS vnic:Fc:name managed object property"
    ::= { cucsVnicFcEntry 14 }

cucsVnicFcNdAddr OBJECT-TYPE
    SYNTAX       Unsigned64
    MAX-ACCESS   read-only
    STATUS       current
    DESCRIPTION
        "Cisco UCS vnic:Fc:nodeAddr managed object property"
    ::= { cucsVnicFcEntry 15 }

cucsVnicFcNwTemplName OBJECT-TYPE
    SYNTAX       SnmpAdminString
    MAX-ACCESS   read-only
    STATUS       current
    DESCRIPTION
        "Cisco UCS vnic:Fc:nwTemplName managed object property"
    ::= { cucsVnicFcEntry 16 }

cucsVnicFcOperAdaptorProfileName OBJECT-TYPE
    SYNTAX       SnmpAdminString
    MAX-ACCESS   read-only
    STATUS       current
    DESCRIPTION
        "Cisco UCS vnic:Fc:operAdaptorProfileName managed object property"
    ::= { cucsVnicFcEntry 17 }

cucsVnicFcOperIdentPoolName OBJECT-TYPE
    SYNTAX       SnmpAdminString
    MAX-ACCESS   read-only
    STATUS       current
    DESCRIPTION
        "Cisco UCS vnic:Fc:operIdentPoolName managed object property"
    ::= { cucsVnicFcEntry 18 }

cucsVnicFcOperNwTemplName OBJECT-TYPE
    SYNTAX       SnmpAdminString
    MAX-ACCESS   read-only
    STATUS       current
    DESCRIPTION
        "Cisco UCS vnic:Fc:operNwTemplName managed object property"
    ::= { cucsVnicFcEntry 19 }

cucsVnicFcOperOrder OBJECT-TYPE
    SYNTAX       Gauge32
    MAX-ACCESS   read-only
    STATUS       current
    DESCRIPTION
        "Cisco UCS vnic:Fc:operOrder managed object property"
    ::= { cucsVnicFcEntry 20 }

cucsVnicFcOperQosPolicyName OBJECT-TYPE
    SYNTAX       SnmpAdminString
    MAX-ACCESS   read-only
    STATUS       current
    DESCRIPTION
        "Cisco UCS vnic:Fc:operQosPolicyName managed object property"
    ::= { cucsVnicFcEntry 21 }

cucsVnicFcOperSpeed OBJECT-TYPE
    SYNTAX       Gauge32
    MAX-ACCESS   read-only
    STATUS       current
    DESCRIPTION
        "Cisco UCS vnic:Fc:operSpeed managed object property"
    ::= { cucsVnicFcEntry 22 }

cucsVnicFcOperStatsPolicyName OBJECT-TYPE
    SYNTAX       SnmpAdminString
    MAX-ACCESS   read-only
    STATUS       current
    DESCRIPTION
        "Cisco UCS vnic:Fc:operStatsPolicyName managed object property"
    ::= { cucsVnicFcEntry 23 }

cucsVnicFcOperVcon OBJECT-TYPE
    SYNTAX       SnmpAdminString
    MAX-ACCESS   read-only
    STATUS       current
    DESCRIPTION
        "Cisco UCS vnic:Fc:operVcon managed object property"
    ::= { cucsVnicFcEntry 24 }

cucsVnicFcOrder OBJECT-TYPE
    SYNTAX       Gauge32
    MAX-ACCESS   read-only
    STATUS       current
    DESCRIPTION
        "Cisco UCS vnic:Fc:order managed object property"
    ::= { cucsVnicFcEntry 25 }

cucsVnicFcOwner OBJECT-TYPE
    SYNTAX       CucsVnicConnectionOwner
    MAX-ACCESS   read-only
    STATUS       current
    DESCRIPTION
        "Cisco UCS vnic:Fc:owner managed object property"
    ::= { cucsVnicFcEntry 26 }

cucsVnicFcPersBind OBJECT-TYPE
    SYNTAX       CucsVnicFcBasePersBind
    MAX-ACCESS   read-only
    STATUS       current
    DESCRIPTION
        "Cisco UCS vnic:Fc:persBind managed object property"
    ::= { cucsVnicFcEntry 27 }

cucsVnicFcPersBindClear OBJECT-TYPE
    SYNTAX       TruthValue
    MAX-ACCESS   read-only
    STATUS       current
    DESCRIPTION
        "Cisco UCS vnic:Fc:persBindClear managed object property"
    ::= { cucsVnicFcEntry 28 }

cucsVnicFcPinToGroupName OBJECT-TYPE
    SYNTAX       SnmpAdminString
    MAX-ACCESS   read-only
    STATUS       current
    DESCRIPTION
        "Cisco UCS vnic:Fc:pinToGroupName managed object property"
    ::= { cucsVnicFcEntry 29 }

cucsVnicFcQosPolicyName OBJECT-TYPE
    SYNTAX       SnmpAdminString
    MAX-ACCESS   read-only
    STATUS       current
    DESCRIPTION
        "Cisco UCS vnic:Fc:qosPolicyName managed object property"
    ::= { cucsVnicFcEntry 30 }

cucsVnicFcStatsPolicyName OBJECT-TYPE
    SYNTAX       SnmpAdminString
    MAX-ACCESS   read-only
    STATUS       current
    DESCRIPTION
        "Cisco UCS vnic:Fc:statsPolicyName managed object property"
    ::= { cucsVnicFcEntry 31 }

cucsVnicFcSwitchId OBJECT-TYPE
    SYNTAX       CucsNetworkSwitchId
    MAX-ACCESS   read-only
    STATUS       current
    DESCRIPTION
        "Cisco UCS vnic:Fc:switchId managed object property"
    ::= { cucsVnicFcEntry 32 }

cucsVnicFcType OBJECT-TYPE
    SYNTAX       CucsVnicFcBaseType
    MAX-ACCESS   read-only
    STATUS       current
    DESCRIPTION
        "Cisco UCS vnic:Fc:type managed object property"
    ::= { cucsVnicFcEntry 33 }

cucsVnicFcOperPinToGroupName OBJECT-TYPE
    SYNTAX       SnmpAdminString
    MAX-ACCESS   read-only
    STATUS       current
    DESCRIPTION
        "Cisco UCS vnic:Fc:operPinToGroupName managed object property"
    ::= { cucsVnicFcEntry 34 }

cucsVnicFcIfTable OBJECT-TYPE
    SYNTAX           SEQUENCE OF CucsVnicFcIfEntry
    MAX-ACCESS       not-accessible
    STATUS           current
    DESCRIPTION
        "Cisco UCS vnic:FcIf managed object table"
    ::= { cucsVnicObjects 12 }

cucsVnicFcIfEntry OBJECT-TYPE
    SYNTAX           CucsVnicFcIfEntry
    MAX-ACCESS       not-accessible
    STATUS           current
    DESCRIPTION
        "Entry for the cucsVnicFcIfTable table."
    INDEX { cucsVnicFcIfInstanceId }
    ::= { cucsVnicFcIfTable 1 }

CucsVnicFcIfEntry ::= SEQUENCE {
    cucsVnicFcIfInstanceId                                           CucsManagedObjectId,
    cucsVnicFcIfDn                                                   CucsManagedObjectDn,
    cucsVnicFcIfRn                                                   SnmpAdminString,
    cucsVnicFcIfInitiator                                            Unsigned64,
    cucsVnicFcIfName                                                 SnmpAdminString,
    cucsVnicFcIfOperState                                            CucsVnicIfOperState,
    cucsVnicFcIfOwner                                                CucsVnicConnectionOwner,
    cucsVnicFcIfSwitchId                                             CucsVnicL2IfSwitchId,
    cucsVnicFcIfType                                                 CucsVnicAFcIfType,
    cucsVnicFcIfVnet                                                 Gauge32,
    cucsVnicFcIfOperVnetDn                                           SnmpAdminString,
    cucsVnicFcIfOperVnetName                                         SnmpAdminString
}

cucsVnicFcIfInstanceId OBJECT-TYPE
    SYNTAX       CucsManagedObjectId
    MAX-ACCESS   not-accessible
    STATUS       current
    DESCRIPTION
        "Instance identifier of the managed object."
    ::= { cucsVnicFcIfEntry 1 }

cucsVnicFcIfDn OBJECT-TYPE
    SYNTAX       CucsManagedObjectDn
    MAX-ACCESS   read-only
    STATUS       current
    DESCRIPTION
        "Cisco UCS vnic:FcIf:dn managed object property"
    ::= { cucsVnicFcIfEntry 2 }

cucsVnicFcIfRn OBJECT-TYPE
    SYNTAX       SnmpAdminString
    MAX-ACCESS   read-only
    STATUS       current
    DESCRIPTION
        "Cisco UCS vnic:FcIf:rn managed object property"
    ::= { cucsVnicFcIfEntry 3 }

cucsVnicFcIfInitiator OBJECT-TYPE
    SYNTAX       Unsigned64
    MAX-ACCESS   read-only
    STATUS       current
    DESCRIPTION
        "Cisco UCS vnic:FcIf:initiator managed object property"
    ::= { cucsVnicFcIfEntry 4 }

cucsVnicFcIfName OBJECT-TYPE
    SYNTAX       SnmpAdminString
    MAX-ACCESS   read-only
    STATUS       current
    DESCRIPTION
        "Cisco UCS vnic:FcIf:name managed object property"
    ::= { cucsVnicFcIfEntry 5 }

cucsVnicFcIfOperState OBJECT-TYPE
    SYNTAX       CucsVnicIfOperState
    MAX-ACCESS   read-only
    STATUS       current
    DESCRIPTION
        "Cisco UCS vnic:FcIf:operState managed object property"
    ::= { cucsVnicFcIfEntry 6 }

cucsVnicFcIfOwner OBJECT-TYPE
    SYNTAX       CucsVnicConnectionOwner
    MAX-ACCESS   read-only
    STATUS       current
    DESCRIPTION
        "Cisco UCS vnic:FcIf:owner managed object property"
    ::= { cucsVnicFcIfEntry 7 }

cucsVnicFcIfSwitchId OBJECT-TYPE
    SYNTAX       CucsVnicL2IfSwitchId
    MAX-ACCESS   read-only
    STATUS       current
    DESCRIPTION
        "Cisco UCS vnic:FcIf:switchId managed object property"
    ::= { cucsVnicFcIfEntry 8 }

cucsVnicFcIfType OBJECT-TYPE
    SYNTAX       CucsVnicAFcIfType
    MAX-ACCESS   read-only
    STATUS       current
    DESCRIPTION
        "Cisco UCS vnic:FcIf:type managed object property"
    ::= { cucsVnicFcIfEntry 9 }

cucsVnicFcIfVnet OBJECT-TYPE
    SYNTAX       Gauge32
    MAX-ACCESS   read-only
    STATUS       current
    DESCRIPTION
        "Cisco UCS vnic:FcIf:vnet managed object property"
    ::= { cucsVnicFcIfEntry 10 }

cucsVnicFcIfOperVnetDn OBJECT-TYPE
    SYNTAX       SnmpAdminString
    MAX-ACCESS   read-only
    STATUS       current
    DESCRIPTION
        "Cisco UCS vnic:FcIf:operVnetDn managed object property"
    ::= { cucsVnicFcIfEntry 11 }

cucsVnicFcIfOperVnetName OBJECT-TYPE
    SYNTAX       SnmpAdminString
    MAX-ACCESS   read-only
    STATUS       current
    DESCRIPTION
        "Cisco UCS vnic:FcIf:operVnetName managed object property"
    ::= { cucsVnicFcIfEntry 12 }

cucsVnicFcLifTable OBJECT-TYPE
    SYNTAX           SEQUENCE OF CucsVnicFcLifEntry
    MAX-ACCESS       not-accessible
    STATUS           current
    DESCRIPTION
        "Cisco UCS vnic:FcLif managed object table"
    ::= { cucsVnicObjects 13 }

cucsVnicFcLifEntry OBJECT-TYPE
    SYNTAX           CucsVnicFcLifEntry
    MAX-ACCESS       not-accessible
    STATUS           current
    DESCRIPTION
        "Entry for the cucsVnicFcLifTable table."
    INDEX { cucsVnicFcLifInstanceId }
    ::= { cucsVnicFcLifTable 1 }

CucsVnicFcLifEntry ::= SEQUENCE {
    cucsVnicFcLifInstanceId                                          CucsManagedObjectId,
    cucsVnicFcLifDn                                                  CucsManagedObjectDn,
    cucsVnicFcLifRn                                                  SnmpAdminString,
    cucsVnicFcLifAddr                                                Unsigned64,
    cucsVnicFcLifName                                                SnmpAdminString,
    cucsVnicFcLifNicDn                                               SnmpAdminString,
    cucsVnicFcLifOwner                                               CucsVnicConnectionOwner,
    cucsVnicFcLifSwitchId                                            CucsNetworkSwitchId,
    cucsVnicFcLifType                                                CucsVnicConnectionType,
    cucsVnicFcLifVnicDn                                              SnmpAdminString
}

cucsVnicFcLifInstanceId OBJECT-TYPE
    SYNTAX       CucsManagedObjectId
    MAX-ACCESS   not-accessible
    STATUS       current
    DESCRIPTION
        "Instance identifier of the managed object."
    ::= { cucsVnicFcLifEntry 1 }

cucsVnicFcLifDn OBJECT-TYPE
    SYNTAX       CucsManagedObjectDn
    MAX-ACCESS   read-only
    STATUS       current
    DESCRIPTION
        "Cisco UCS vnic:FcLif:dn managed object property"
    ::= { cucsVnicFcLifEntry 2 }

cucsVnicFcLifRn OBJECT-TYPE
    SYNTAX       SnmpAdminString
    MAX-ACCESS   read-only
    STATUS       current
    DESCRIPTION
        "Cisco UCS vnic:FcLif:rn managed object property"
    ::= { cucsVnicFcLifEntry 3 }

cucsVnicFcLifAddr OBJECT-TYPE
    SYNTAX       Unsigned64
    MAX-ACCESS   read-only
    STATUS       current
    DESCRIPTION
        "Cisco UCS vnic:FcLif:addr managed object property"
    ::= { cucsVnicFcLifEntry 4 }

cucsVnicFcLifName OBJECT-TYPE
    SYNTAX       SnmpAdminString
    MAX-ACCESS   read-only
    STATUS       current
    DESCRIPTION
        "Cisco UCS vnic:FcLif:name managed object property"
    ::= { cucsVnicFcLifEntry 5 }

cucsVnicFcLifNicDn OBJECT-TYPE
    SYNTAX       SnmpAdminString
    MAX-ACCESS   read-only
    STATUS       current
    DESCRIPTION
        "Cisco UCS vnic:FcLif:nicDn managed object property"
    ::= { cucsVnicFcLifEntry 6 }

cucsVnicFcLifOwner OBJECT-TYPE
    SYNTAX       CucsVnicConnectionOwner
    MAX-ACCESS   read-only
    STATUS       current
    DESCRIPTION
        "Cisco UCS vnic:FcLif:owner managed object property"
    ::= { cucsVnicFcLifEntry 7 }

cucsVnicFcLifSwitchId OBJECT-TYPE
    SYNTAX       CucsNetworkSwitchId
    MAX-ACCESS   read-only
    STATUS       current
    DESCRIPTION
        "Cisco UCS vnic:FcLif:switchId managed object property"
    ::= { cucsVnicFcLifEntry 8 }

cucsVnicFcLifType OBJECT-TYPE
    SYNTAX       CucsVnicConnectionType
    MAX-ACCESS   read-only
    STATUS       current
    DESCRIPTION
        "Cisco UCS vnic:FcLif:type managed object property"
    ::= { cucsVnicFcLifEntry 9 }

cucsVnicFcLifVnicDn OBJECT-TYPE
    SYNTAX       SnmpAdminString
    MAX-ACCESS   read-only
    STATUS       current
    DESCRIPTION
        "Cisco UCS vnic:FcLif:vnicDn managed object property"
    ::= { cucsVnicFcLifEntry 10 }

cucsVnicFcNodeTable OBJECT-TYPE
    SYNTAX           SEQUENCE OF CucsVnicFcNodeEntry
    MAX-ACCESS       not-accessible
    STATUS           current
    DESCRIPTION
        "Cisco UCS vnic:FcNode managed object table"
    ::= { cucsVnicObjects 14 }

cucsVnicFcNodeEntry OBJECT-TYPE
    SYNTAX           CucsVnicFcNodeEntry
    MAX-ACCESS       not-accessible
    STATUS           current
    DESCRIPTION
        "Entry for the cucsVnicFcNodeTable table."
    INDEX { cucsVnicFcNodeInstanceId }
    ::= { cucsVnicFcNodeTable 1 }

CucsVnicFcNodeEntry ::= SEQUENCE {
    cucsVnicFcNodeInstanceId                                         CucsManagedObjectId,
    cucsVnicFcNodeDn                                                 CucsManagedObjectDn,
    cucsVnicFcNodeRn                                                 SnmpAdminString,
    cucsVnicFcNodeAddr                                               Unsigned64,
    cucsVnicFcNodeFltAggr                                            Unsigned64,
    cucsVnicFcNodeIdentPoolName                                      SnmpAdminString,
    cucsVnicFcNodeOperIdentPoolName                                  SnmpAdminString
}

cucsVnicFcNodeInstanceId OBJECT-TYPE
    SYNTAX       CucsManagedObjectId
    MAX-ACCESS   not-accessible
    STATUS       current
    DESCRIPTION
        "Instance identifier of the managed object."
    ::= { cucsVnicFcNodeEntry 1 }

cucsVnicFcNodeDn OBJECT-TYPE
    SYNTAX       CucsManagedObjectDn
    MAX-ACCESS   read-only
    STATUS       current
    DESCRIPTION
        "Cisco UCS vnic:FcNode:dn managed object property"
    ::= { cucsVnicFcNodeEntry 2 }

cucsVnicFcNodeRn OBJECT-TYPE
    SYNTAX       SnmpAdminString
    MAX-ACCESS   read-only
    STATUS       current
    DESCRIPTION
        "Cisco UCS vnic:FcNode:rn managed object property"
    ::= { cucsVnicFcNodeEntry 3 }

cucsVnicFcNodeAddr OBJECT-TYPE
    SYNTAX       Unsigned64
    MAX-ACCESS   read-only
    STATUS       current
    DESCRIPTION
        "Cisco UCS vnic:FcNode:addr managed object property"
    ::= { cucsVnicFcNodeEntry 4 }

cucsVnicFcNodeFltAggr OBJECT-TYPE
    SYNTAX       Unsigned64
    MAX-ACCESS   read-only
    STATUS       current
    DESCRIPTION
        "Cisco UCS vnic:FcNode:fltAggr managed object property"
    ::= { cucsVnicFcNodeEntry 5 }

cucsVnicFcNodeIdentPoolName OBJECT-TYPE
    SYNTAX       SnmpAdminString
    MAX-ACCESS   read-only
    STATUS       current
    DESCRIPTION
        "Cisco UCS vnic:FcNode:identPoolName managed object property"
    ::= { cucsVnicFcNodeEntry 6 }

cucsVnicFcNodeOperIdentPoolName OBJECT-TYPE
    SYNTAX       SnmpAdminString
    MAX-ACCESS   read-only
    STATUS       current
    DESCRIPTION
        "Cisco UCS vnic:FcNode:operIdentPoolName managed object property"
    ::= { cucsVnicFcNodeEntry 7 }

cucsVnicFcOEIfTable OBJECT-TYPE
    SYNTAX           SEQUENCE OF CucsVnicFcOEIfEntry
    MAX-ACCESS       not-accessible
    STATUS           current
    DESCRIPTION
        "Cisco UCS vnic:FcOEIf managed object table"
    ::= { cucsVnicObjects 15 }

cucsVnicFcOEIfEntry OBJECT-TYPE
    SYNTAX           CucsVnicFcOEIfEntry
    MAX-ACCESS       not-accessible
    STATUS           current
    DESCRIPTION
        "Entry for the cucsVnicFcOEIfTable table."
    INDEX { cucsVnicFcOEIfInstanceId }
    ::= { cucsVnicFcOEIfTable 1 }

CucsVnicFcOEIfEntry ::= SEQUENCE {
    cucsVnicFcOEIfInstanceId                                         CucsManagedObjectId,
    cucsVnicFcOEIfDn                                                 CucsManagedObjectDn,
    cucsVnicFcOEIfRn                                                 SnmpAdminString,
    cucsVnicFcOEIfInitiator                                          Unsigned64,
    cucsVnicFcOEIfName                                               SnmpAdminString,
    cucsVnicFcOEIfOperState                                          CucsVnicIfOperState,
    cucsVnicFcOEIfOwner                                              CucsVnicConnectionOwner,
    cucsVnicFcOEIfSwitchId                                           CucsVnicL2IfSwitchId,
    cucsVnicFcOEIfType                                               CucsVnicAFcIfType,
    cucsVnicFcOEIfVnet                                               Gauge32
}

cucsVnicFcOEIfInstanceId OBJECT-TYPE
    SYNTAX       CucsManagedObjectId
    MAX-ACCESS   not-accessible
    STATUS       current
    DESCRIPTION
        "Instance identifier of the managed object."
    ::= { cucsVnicFcOEIfEntry 1 }

cucsVnicFcOEIfDn OBJECT-TYPE
    SYNTAX       CucsManagedObjectDn
    MAX-ACCESS   read-only
    STATUS       current
    DESCRIPTION
        "Cisco UCS vnic:FcOEIf:dn managed object property"
    ::= { cucsVnicFcOEIfEntry 2 }

cucsVnicFcOEIfRn OBJECT-TYPE
    SYNTAX       SnmpAdminString
    MAX-ACCESS   read-only
    STATUS       current
    DESCRIPTION
        "Cisco UCS vnic:FcOEIf:rn managed object property"
    ::= { cucsVnicFcOEIfEntry 3 }

cucsVnicFcOEIfInitiator OBJECT-TYPE
    SYNTAX       Unsigned64
    MAX-ACCESS   read-only
    STATUS       current
    DESCRIPTION
        "Cisco UCS vnic:FcOEIf:initiator managed object property"
    ::= { cucsVnicFcOEIfEntry 4 }

cucsVnicFcOEIfName OBJECT-TYPE
    SYNTAX       SnmpAdminString
    MAX-ACCESS   read-only
    STATUS       current
    DESCRIPTION
        "Cisco UCS vnic:FcOEIf:name managed object property"
    ::= { cucsVnicFcOEIfEntry 5 }

cucsVnicFcOEIfOperState OBJECT-TYPE
    SYNTAX       CucsVnicIfOperState
    MAX-ACCESS   read-only
    STATUS       current
    DESCRIPTION
        "Cisco UCS vnic:FcOEIf:operState managed object property"
    ::= { cucsVnicFcOEIfEntry 6 }

cucsVnicFcOEIfOwner OBJECT-TYPE
    SYNTAX       CucsVnicConnectionOwner
    MAX-ACCESS   read-only
    STATUS       current
    DESCRIPTION
        "Cisco UCS vnic:FcOEIf:owner managed object property"
    ::= { cucsVnicFcOEIfEntry 7 }

cucsVnicFcOEIfSwitchId OBJECT-TYPE
    SYNTAX       CucsVnicL2IfSwitchId
    MAX-ACCESS   read-only
    STATUS       current
    DESCRIPTION
        "Cisco UCS vnic:FcOEIf:switchId managed object property"
    ::= { cucsVnicFcOEIfEntry 8 }

cucsVnicFcOEIfType OBJECT-TYPE
    SYNTAX       CucsVnicAFcIfType
    MAX-ACCESS   read-only
    STATUS       current
    DESCRIPTION
        "Cisco UCS vnic:FcOEIf:type managed object property"
    ::= { cucsVnicFcOEIfEntry 9 }

cucsVnicFcOEIfVnet OBJECT-TYPE
    SYNTAX       Gauge32
    MAX-ACCESS   read-only
    STATUS       current
    DESCRIPTION
        "Cisco UCS vnic:FcOEIf:vnet managed object property"
    ::= { cucsVnicFcOEIfEntry 10 }

cucsVnicIPv4DhcpTable OBJECT-TYPE
    SYNTAX           SEQUENCE OF CucsVnicIPv4DhcpEntry
    MAX-ACCESS       not-accessible
    STATUS           current
    DESCRIPTION
        "Cisco UCS vnic:IPv4Dhcp managed object table"
    ::= { cucsVnicObjects 16 }

cucsVnicIPv4DhcpEntry OBJECT-TYPE
    SYNTAX           CucsVnicIPv4DhcpEntry
    MAX-ACCESS       not-accessible
    STATUS           current
    DESCRIPTION
        "Entry for the cucsVnicIPv4DhcpTable table."
    INDEX { cucsVnicIPv4DhcpInstanceId }
    ::= { cucsVnicIPv4DhcpTable 1 }

CucsVnicIPv4DhcpEntry ::= SEQUENCE {
    cucsVnicIPv4DhcpInstanceId                                       CucsManagedObjectId,
    cucsVnicIPv4DhcpDn                                               CucsManagedObjectDn,
    cucsVnicIPv4DhcpRn                                               SnmpAdminString,
    cucsVnicIPv4DhcpAddr                                             InetAddressIPv4,
    cucsVnicIPv4DhcpDefGw                                            InetAddressIPv4,
    cucsVnicIPv4DhcpSubnet                                           InetAddressIPv4
}

cucsVnicIPv4DhcpInstanceId OBJECT-TYPE
    SYNTAX       CucsManagedObjectId
    MAX-ACCESS   not-accessible
    STATUS       current
    DESCRIPTION
        "Instance identifier of the managed object."
    ::= { cucsVnicIPv4DhcpEntry 1 }

cucsVnicIPv4DhcpDn OBJECT-TYPE
    SYNTAX       CucsManagedObjectDn
    MAX-ACCESS   read-only
    STATUS       current
    DESCRIPTION
        "Cisco UCS vnic:IPv4Dhcp:dn managed object property"
    ::= { cucsVnicIPv4DhcpEntry 2 }

cucsVnicIPv4DhcpRn OBJECT-TYPE
    SYNTAX       SnmpAdminString
    MAX-ACCESS   read-only
    STATUS       current
    DESCRIPTION
        "Cisco UCS vnic:IPv4Dhcp:rn managed object property"
    ::= { cucsVnicIPv4DhcpEntry 3 }

cucsVnicIPv4DhcpAddr OBJECT-TYPE
    SYNTAX       InetAddressIPv4
    MAX-ACCESS   read-only
    STATUS       current
    DESCRIPTION
        "Cisco UCS vnic:IPv4Dhcp:addr managed object property"
    ::= { cucsVnicIPv4DhcpEntry 4 }

cucsVnicIPv4DhcpDefGw OBJECT-TYPE
    SYNTAX       InetAddressIPv4
    MAX-ACCESS   read-only
    STATUS       current
    DESCRIPTION
        "Cisco UCS vnic:IPv4Dhcp:defGw managed object property"
    ::= { cucsVnicIPv4DhcpEntry 5 }

cucsVnicIPv4DhcpSubnet OBJECT-TYPE
    SYNTAX       InetAddressIPv4
    MAX-ACCESS   read-only
    STATUS       current
    DESCRIPTION
        "Cisco UCS vnic:IPv4Dhcp:subnet managed object property"
    ::= { cucsVnicIPv4DhcpEntry 6 }

cucsVnicIPv4DnsTable OBJECT-TYPE
    SYNTAX           SEQUENCE OF CucsVnicIPv4DnsEntry
    MAX-ACCESS       not-accessible
    STATUS           current
    DESCRIPTION
        "Cisco UCS vnic:IPv4Dns managed object table"
    ::= { cucsVnicObjects 17 }

cucsVnicIPv4DnsEntry OBJECT-TYPE
    SYNTAX           CucsVnicIPv4DnsEntry
    MAX-ACCESS       not-accessible
    STATUS           current
    DESCRIPTION
        "Entry for the cucsVnicIPv4DnsTable table."
    INDEX { cucsVnicIPv4DnsInstanceId }
    ::= { cucsVnicIPv4DnsTable 1 }

CucsVnicIPv4DnsEntry ::= SEQUENCE {
    cucsVnicIPv4DnsInstanceId                                        CucsManagedObjectId,
    cucsVnicIPv4DnsDn                                                CucsManagedObjectDn,
    cucsVnicIPv4DnsRn                                                SnmpAdminString,
    cucsVnicIPv4DnsAddr                                              InetAddressIPv4,
    cucsVnicIPv4DnsDefGw                                             InetAddressIPv4,
    cucsVnicIPv4DnsPref                                              CucsVnicIPv4DnsPref,
    cucsVnicIPv4DnsSubnet                                            InetAddressIPv4
}

cucsVnicIPv4DnsInstanceId OBJECT-TYPE
    SYNTAX       CucsManagedObjectId
    MAX-ACCESS   not-accessible
    STATUS       current
    DESCRIPTION
        "Instance identifier of the managed object."
    ::= { cucsVnicIPv4DnsEntry 1 }

cucsVnicIPv4DnsDn OBJECT-TYPE
    SYNTAX       CucsManagedObjectDn
    MAX-ACCESS   read-only
    STATUS       current
    DESCRIPTION
        "Cisco UCS vnic:IPv4Dns:dn managed object property"
    ::= { cucsVnicIPv4DnsEntry 2 }

cucsVnicIPv4DnsRn OBJECT-TYPE
    SYNTAX       SnmpAdminString
    MAX-ACCESS   read-only
    STATUS       current
    DESCRIPTION
        "Cisco UCS vnic:IPv4Dns:rn managed object property"
    ::= { cucsVnicIPv4DnsEntry 3 }

cucsVnicIPv4DnsAddr OBJECT-TYPE
    SYNTAX       InetAddressIPv4
    MAX-ACCESS   read-only
    STATUS       current
    DESCRIPTION
        "Cisco UCS vnic:IPv4Dns:addr managed object property"
    ::= { cucsVnicIPv4DnsEntry 4 }

cucsVnicIPv4DnsDefGw OBJECT-TYPE
    SYNTAX       InetAddressIPv4
    MAX-ACCESS   read-only
    STATUS       current
    DESCRIPTION
        "Cisco UCS vnic:IPv4Dns:defGw managed object property"
    ::= { cucsVnicIPv4DnsEntry 5 }

cucsVnicIPv4DnsPref OBJECT-TYPE
    SYNTAX       CucsVnicIPv4DnsPref
    MAX-ACCESS   read-only
    STATUS       current
    DESCRIPTION
        "Cisco UCS vnic:IPv4Dns:pref managed object property"
    ::= { cucsVnicIPv4DnsEntry 6 }

cucsVnicIPv4DnsSubnet OBJECT-TYPE
    SYNTAX       InetAddressIPv4
    MAX-ACCESS   read-only
    STATUS       current
    DESCRIPTION
        "Cisco UCS vnic:IPv4Dns:subnet managed object property"
    ::= { cucsVnicIPv4DnsEntry 7 }

cucsVnicIPv4IfTable OBJECT-TYPE
    SYNTAX           SEQUENCE OF CucsVnicIPv4IfEntry
    MAX-ACCESS       not-accessible
    STATUS           current
    DESCRIPTION
        "Cisco UCS vnic:IPv4If managed object table"
    ::= { cucsVnicObjects 18 }

cucsVnicIPv4IfEntry OBJECT-TYPE
    SYNTAX           CucsVnicIPv4IfEntry
    MAX-ACCESS       not-accessible
    STATUS           current
    DESCRIPTION
        "Entry for the cucsVnicIPv4IfTable table."
    INDEX { cucsVnicIPv4IfInstanceId }
    ::= { cucsVnicIPv4IfTable 1 }

CucsVnicIPv4IfEntry ::= SEQUENCE {
    cucsVnicIPv4IfInstanceId                                         CucsManagedObjectId,
    cucsVnicIPv4IfDn                                                 CucsManagedObjectDn,
    cucsVnicIPv4IfRn                                                 SnmpAdminString,
    cucsVnicIPv4IfAddr                                               InetAddressIPv4,
    cucsVnicIPv4IfName                                               SnmpAdminString,
    cucsVnicIPv4IfOperState                                          CucsVnicIfOperState,
    cucsVnicIPv4IfOwner                                              CucsVnicConnectionOwner,
    cucsVnicIPv4IfSwitchId                                           CucsNetworkSwitchId,
    cucsVnicIPv4IfType                                               CucsVnicConnectionType,
    cucsVnicIPv4IfVnet                                               Gauge32
}

cucsVnicIPv4IfInstanceId OBJECT-TYPE
    SYNTAX       CucsManagedObjectId
    MAX-ACCESS   not-accessible
    STATUS       current
    DESCRIPTION
        "Instance identifier of the managed object."
    ::= { cucsVnicIPv4IfEntry 1 }

cucsVnicIPv4IfDn OBJECT-TYPE
    SYNTAX       CucsManagedObjectDn
    MAX-ACCESS   read-only
    STATUS       current
    DESCRIPTION
        "Cisco UCS vnic:IPv4If:dn managed object property"
    ::= { cucsVnicIPv4IfEntry 2 }

cucsVnicIPv4IfRn OBJECT-TYPE
    SYNTAX       SnmpAdminString
    MAX-ACCESS   read-only
    STATUS       current
    DESCRIPTION
        "Cisco UCS vnic:IPv4If:rn managed object property"
    ::= { cucsVnicIPv4IfEntry 3 }

cucsVnicIPv4IfAddr OBJECT-TYPE
    SYNTAX       InetAddressIPv4
    MAX-ACCESS   read-only
    STATUS       current
    DESCRIPTION
        "Cisco UCS vnic:IPv4If:addr managed object property"
    ::= { cucsVnicIPv4IfEntry 4 }

cucsVnicIPv4IfName OBJECT-TYPE
    SYNTAX       SnmpAdminString
    MAX-ACCESS   read-only
    STATUS       current
    DESCRIPTION
        "Cisco UCS vnic:IPv4If:name managed object property"
    ::= { cucsVnicIPv4IfEntry 5 }

cucsVnicIPv4IfOperState OBJECT-TYPE
    SYNTAX       CucsVnicIfOperState
    MAX-ACCESS   read-only
    STATUS       current
    DESCRIPTION
        "Cisco UCS vnic:IPv4If:operState managed object property"
    ::= { cucsVnicIPv4IfEntry 6 }

cucsVnicIPv4IfOwner OBJECT-TYPE
    SYNTAX       CucsVnicConnectionOwner
    MAX-ACCESS   read-only
    STATUS       current
    DESCRIPTION
        "Cisco UCS vnic:IPv4If:owner managed object property"
    ::= { cucsVnicIPv4IfEntry 7 }

cucsVnicIPv4IfSwitchId OBJECT-TYPE
    SYNTAX       CucsNetworkSwitchId
    MAX-ACCESS   read-only
    STATUS       current
    DESCRIPTION
        "Cisco UCS vnic:IPv4If:switchId managed object property"
    ::= { cucsVnicIPv4IfEntry 8 }

cucsVnicIPv4IfType OBJECT-TYPE
    SYNTAX       CucsVnicConnectionType
    MAX-ACCESS   read-only
    STATUS       current
    DESCRIPTION
        "Cisco UCS vnic:IPv4If:type managed object property"
    ::= { cucsVnicIPv4IfEntry 9 }

cucsVnicIPv4IfVnet OBJECT-TYPE
    SYNTAX       Gauge32
    MAX-ACCESS   read-only
    STATUS       current
    DESCRIPTION
        "Cisco UCS vnic:IPv4If:vnet managed object property"
    ::= { cucsVnicIPv4IfEntry 10 }

cucsVnicIPv4IscsiAddrTable OBJECT-TYPE
    SYNTAX           SEQUENCE OF CucsVnicIPv4IscsiAddrEntry
    MAX-ACCESS       not-accessible
    STATUS           current
    DESCRIPTION
        "Cisco UCS vnic:IPv4IscsiAddr managed object table"
    ::= { cucsVnicObjects 36 }

cucsVnicIPv4IscsiAddrEntry OBJECT-TYPE
    SYNTAX           CucsVnicIPv4IscsiAddrEntry
    MAX-ACCESS       not-accessible
    STATUS           current
    DESCRIPTION
        "Entry for the cucsVnicIPv4IscsiAddrTable table."
    INDEX { cucsVnicIPv4IscsiAddrInstanceId }
    ::= { cucsVnicIPv4IscsiAddrTable 1 }

CucsVnicIPv4IscsiAddrEntry ::= SEQUENCE {
    cucsVnicIPv4IscsiAddrInstanceId                                  CucsManagedObjectId,
    cucsVnicIPv4IscsiAddrDn                                          CucsManagedObjectDn,
    cucsVnicIPv4IscsiAddrRn                                          SnmpAdminString,
    cucsVnicIPv4IscsiAddrAddr                                        InetAddressIPv4,
    cucsVnicIPv4IscsiAddrDefGw                                       InetAddressIPv4,
    cucsVnicIPv4IscsiAddrPrimDns                                     InetAddressIPv4,
    cucsVnicIPv4IscsiAddrSecDns                                      InetAddressIPv4,
    cucsVnicIPv4IscsiAddrSubnet                                      InetAddressIPv4
}

cucsVnicIPv4IscsiAddrInstanceId OBJECT-TYPE
    SYNTAX       CucsManagedObjectId
    MAX-ACCESS   not-accessible
    STATUS       current
    DESCRIPTION
        "Instance identifier of the managed object."
    ::= { cucsVnicIPv4IscsiAddrEntry 1 }

cucsVnicIPv4IscsiAddrDn OBJECT-TYPE
    SYNTAX       CucsManagedObjectDn
    MAX-ACCESS   read-only
    STATUS       current
    DESCRIPTION
        "Cisco UCS vnic:IPv4IscsiAddr:dn managed object property"
    ::= { cucsVnicIPv4IscsiAddrEntry 2 }

cucsVnicIPv4IscsiAddrRn OBJECT-TYPE
    SYNTAX       SnmpAdminString
    MAX-ACCESS   read-only
    STATUS       current
    DESCRIPTION
        "Cisco UCS vnic:IPv4IscsiAddr:rn managed object property"
    ::= { cucsVnicIPv4IscsiAddrEntry 3 }

cucsVnicIPv4IscsiAddrAddr OBJECT-TYPE
    SYNTAX       InetAddressIPv4
    MAX-ACCESS   read-only
    STATUS       current
    DESCRIPTION
        "Cisco UCS vnic:IPv4IscsiAddr:addr managed object property"
    ::= { cucsVnicIPv4IscsiAddrEntry 4 }

cucsVnicIPv4IscsiAddrDefGw OBJECT-TYPE
    SYNTAX       InetAddressIPv4
    MAX-ACCESS   read-only
    STATUS       current
    DESCRIPTION
        "Cisco UCS vnic:IPv4IscsiAddr:defGw managed object property"
    ::= { cucsVnicIPv4IscsiAddrEntry 5 }

cucsVnicIPv4IscsiAddrPrimDns OBJECT-TYPE
    SYNTAX       InetAddressIPv4
    MAX-ACCESS   read-only
    STATUS       current
    DESCRIPTION
        "Cisco UCS vnic:IPv4IscsiAddr:primDns managed object property"
    ::= { cucsVnicIPv4IscsiAddrEntry 6 }

cucsVnicIPv4IscsiAddrSecDns OBJECT-TYPE
    SYNTAX       InetAddressIPv4
    MAX-ACCESS   read-only
    STATUS       current
    DESCRIPTION
        "Cisco UCS vnic:IPv4IscsiAddr:secDns managed object property"
    ::= { cucsVnicIPv4IscsiAddrEntry 7 }

cucsVnicIPv4IscsiAddrSubnet OBJECT-TYPE
    SYNTAX       InetAddressIPv4
    MAX-ACCESS   read-only
    STATUS       current
    DESCRIPTION
        "Cisco UCS vnic:IPv4IscsiAddr:subnet managed object property"
    ::= { cucsVnicIPv4IscsiAddrEntry 8 }

cucsVnicIPv4PooledIscsiAddrTable OBJECT-TYPE
    SYNTAX           SEQUENCE OF CucsVnicIPv4PooledIscsiAddrEntry
    MAX-ACCESS       not-accessible
    STATUS           current
    DESCRIPTION
        "Cisco UCS vnic:IPv4PooledIscsiAddr managed object table"
    ::= { cucsVnicObjects 37 }

cucsVnicIPv4PooledIscsiAddrEntry OBJECT-TYPE
    SYNTAX           CucsVnicIPv4PooledIscsiAddrEntry
    MAX-ACCESS       not-accessible
    STATUS           current
    DESCRIPTION
        "Entry for the cucsVnicIPv4PooledIscsiAddrTable table."
    INDEX { cucsVnicIPv4PooledIscsiAddrInstanceId }
    ::= { cucsVnicIPv4PooledIscsiAddrTable 1 }

CucsVnicIPv4PooledIscsiAddrEntry ::= SEQUENCE {
    cucsVnicIPv4PooledIscsiAddrInstanceId                            CucsManagedObjectId,
    cucsVnicIPv4PooledIscsiAddrDn                                    CucsManagedObjectDn,
    cucsVnicIPv4PooledIscsiAddrRn                                    SnmpAdminString,
    cucsVnicIPv4PooledIscsiAddrAddr                                  InetAddressIPv4,
    cucsVnicIPv4PooledIscsiAddrDefGw                                 InetAddressIPv4,
    cucsVnicIPv4PooledIscsiAddrIdentPoolName                         SnmpAdminString,
    cucsVnicIPv4PooledIscsiAddrOperIdentPoolName                     SnmpAdminString,
    cucsVnicIPv4PooledIscsiAddrPrimDns                               InetAddressIPv4,
    cucsVnicIPv4PooledIscsiAddrSecDns                                InetAddressIPv4,
    cucsVnicIPv4PooledIscsiAddrSubnet                                InetAddressIPv4
}

cucsVnicIPv4PooledIscsiAddrInstanceId OBJECT-TYPE
    SYNTAX       CucsManagedObjectId
    MAX-ACCESS   not-accessible
    STATUS       current
    DESCRIPTION
        "Instance identifier of the managed object."
    ::= { cucsVnicIPv4PooledIscsiAddrEntry 1 }

cucsVnicIPv4PooledIscsiAddrDn OBJECT-TYPE
    SYNTAX       CucsManagedObjectDn
    MAX-ACCESS   read-only
    STATUS       current
    DESCRIPTION
        "Cisco UCS vnic:IPv4PooledIscsiAddr:dn managed object property"
    ::= { cucsVnicIPv4PooledIscsiAddrEntry 2 }

cucsVnicIPv4PooledIscsiAddrRn OBJECT-TYPE
    SYNTAX       SnmpAdminString
    MAX-ACCESS   read-only
    STATUS       current
    DESCRIPTION
        "Cisco UCS vnic:IPv4PooledIscsiAddr:rn managed object property"
    ::= { cucsVnicIPv4PooledIscsiAddrEntry 3 }

cucsVnicIPv4PooledIscsiAddrAddr OBJECT-TYPE
    SYNTAX       InetAddressIPv4
    MAX-ACCESS   read-only
    STATUS       current
    DESCRIPTION
        "Cisco UCS vnic:IPv4PooledIscsiAddr:addr managed object property"
    ::= { cucsVnicIPv4PooledIscsiAddrEntry 4 }

cucsVnicIPv4PooledIscsiAddrDefGw OBJECT-TYPE
    SYNTAX       InetAddressIPv4
    MAX-ACCESS   read-only
    STATUS       current
    DESCRIPTION
        "Cisco UCS vnic:IPv4PooledIscsiAddr:defGw managed object property"
    ::= { cucsVnicIPv4PooledIscsiAddrEntry 5 }

cucsVnicIPv4PooledIscsiAddrIdentPoolName OBJECT-TYPE
    SYNTAX       SnmpAdminString
    MAX-ACCESS   read-only
    STATUS       current
    DESCRIPTION
        "Cisco UCS vnic:IPv4PooledIscsiAddr:identPoolName
        managed object property"
    ::= { cucsVnicIPv4PooledIscsiAddrEntry 6 }

cucsVnicIPv4PooledIscsiAddrOperIdentPoolName OBJECT-TYPE
    SYNTAX       SnmpAdminString
    MAX-ACCESS   read-only
    STATUS       current
    DESCRIPTION
        "Cisco UCS vnic:IPv4PooledIscsiAddr:operIdentPoolName
        managed object property"
    ::= { cucsVnicIPv4PooledIscsiAddrEntry 7 }

cucsVnicIPv4PooledIscsiAddrPrimDns OBJECT-TYPE
    SYNTAX       InetAddressIPv4
    MAX-ACCESS   read-only
    STATUS       current
    DESCRIPTION
        "Cisco UCS vnic:IPv4PooledIscsiAddr:primDns managed
        object property"
    ::= { cucsVnicIPv4PooledIscsiAddrEntry 8 }

cucsVnicIPv4PooledIscsiAddrSecDns OBJECT-TYPE
    SYNTAX       InetAddressIPv4
    MAX-ACCESS   read-only
    STATUS       current
    DESCRIPTION
        "Cisco UCS vnic:IPv4PooledIscsiAddr:secDns managed
        object property"
    ::= { cucsVnicIPv4PooledIscsiAddrEntry 9 }

cucsVnicIPv4PooledIscsiAddrSubnet OBJECT-TYPE
    SYNTAX       InetAddressIPv4
    MAX-ACCESS   read-only
    STATUS       current
    DESCRIPTION
        "Cisco UCS vnic:IPv4PooledIscsiAddr:subnet managed
        object property"
    ::= { cucsVnicIPv4PooledIscsiAddrEntry 10 }

cucsVnicIPv4StaticRouteTable OBJECT-TYPE
    SYNTAX           SEQUENCE OF CucsVnicIPv4StaticRouteEntry
    MAX-ACCESS       not-accessible
    STATUS           current
    DESCRIPTION
        "Cisco UCS vnic:IPv4StaticRoute managed object table"
    ::= { cucsVnicObjects 19 }

cucsVnicIPv4StaticRouteEntry OBJECT-TYPE
    SYNTAX           CucsVnicIPv4StaticRouteEntry
    MAX-ACCESS       not-accessible
    STATUS           current
    DESCRIPTION
        "Entry for the cucsVnicIPv4StaticRouteTable table."
    INDEX { cucsVnicIPv4StaticRouteInstanceId }
    ::= { cucsVnicIPv4StaticRouteTable 1 }

CucsVnicIPv4StaticRouteEntry ::= SEQUENCE {
    cucsVnicIPv4StaticRouteInstanceId                                CucsManagedObjectId,
    cucsVnicIPv4StaticRouteDn                                        CucsManagedObjectDn,
    cucsVnicIPv4StaticRouteRn                                        SnmpAdminString,
    cucsVnicIPv4StaticRouteAddr                                      InetAddressIPv4,
    cucsVnicIPv4StaticRouteDefGw                                     InetAddressIPv4,
    cucsVnicIPv4StaticRouteGwAddr                                    InetAddressIPv4,
    cucsVnicIPv4StaticRouteGwSubnet                                  InetAddressIPv4,
    cucsVnicIPv4StaticRouteSubnet                                    InetAddressIPv4
}

cucsVnicIPv4StaticRouteInstanceId OBJECT-TYPE
    SYNTAX       CucsManagedObjectId
    MAX-ACCESS   not-accessible
    STATUS       current
    DESCRIPTION
        "Instance identifier of the managed object."
    ::= { cucsVnicIPv4StaticRouteEntry 1 }

cucsVnicIPv4StaticRouteDn OBJECT-TYPE
    SYNTAX       CucsManagedObjectDn
    MAX-ACCESS   read-only
    STATUS       current
    DESCRIPTION
        "Cisco UCS vnic:IPv4StaticRoute:dn managed object property"
    ::= { cucsVnicIPv4StaticRouteEntry 2 }

cucsVnicIPv4StaticRouteRn OBJECT-TYPE
    SYNTAX       SnmpAdminString
    MAX-ACCESS   read-only
    STATUS       current
    DESCRIPTION
        "Cisco UCS vnic:IPv4StaticRoute:rn managed object property"
    ::= { cucsVnicIPv4StaticRouteEntry 3 }

cucsVnicIPv4StaticRouteAddr OBJECT-TYPE
    SYNTAX       InetAddressIPv4
    MAX-ACCESS   read-only
    STATUS       current
    DESCRIPTION
        "Cisco UCS vnic:IPv4StaticRoute:addr managed object property"
    ::= { cucsVnicIPv4StaticRouteEntry 4 }

cucsVnicIPv4StaticRouteDefGw OBJECT-TYPE
    SYNTAX       InetAddressIPv4
    MAX-ACCESS   read-only
    STATUS       current
    DESCRIPTION
        "Cisco UCS vnic:IPv4StaticRoute:defGw managed object property"
    ::= { cucsVnicIPv4StaticRouteEntry 5 }

cucsVnicIPv4StaticRouteGwAddr OBJECT-TYPE
    SYNTAX       InetAddressIPv4
    MAX-ACCESS   read-only
    STATUS       current
    DESCRIPTION
        "Cisco UCS vnic:IPv4StaticRoute:gwAddr managed object property"
    ::= { cucsVnicIPv4StaticRouteEntry 6 }

cucsVnicIPv4StaticRouteGwSubnet OBJECT-TYPE
    SYNTAX       InetAddressIPv4
    MAX-ACCESS   read-only
    STATUS       current
    DESCRIPTION
        "Cisco UCS vnic:IPv4StaticRoute:gwSubnet managed object property"
    ::= { cucsVnicIPv4StaticRouteEntry 7 }

cucsVnicIPv4StaticRouteSubnet OBJECT-TYPE
    SYNTAX       InetAddressIPv4
    MAX-ACCESS   read-only
    STATUS       current
    DESCRIPTION
        "Cisco UCS vnic:IPv4StaticRoute:subnet managed object property"
    ::= { cucsVnicIPv4StaticRouteEntry 8 }

cucsVnicIScsiTable OBJECT-TYPE
    SYNTAX           SEQUENCE OF CucsVnicIScsiEntry
    MAX-ACCESS       not-accessible
    STATUS           current
    DESCRIPTION
        "Cisco UCS vnic:IScsi managed object table"
    ::= { cucsVnicObjects 38 }

cucsVnicIScsiEntry OBJECT-TYPE
    SYNTAX           CucsVnicIScsiEntry
    MAX-ACCESS       not-accessible
    STATUS           current
    DESCRIPTION
        "Entry for the cucsVnicIScsiTable table."
    INDEX { cucsVnicIScsiInstanceId }
    ::= { cucsVnicIScsiTable 1 }

CucsVnicIScsiEntry ::= SEQUENCE {
    cucsVnicIScsiInstanceId                                          CucsManagedObjectId,
    cucsVnicIScsiDn                                                  CucsManagedObjectDn,
    cucsVnicIScsiRn                                                  SnmpAdminString,
    cucsVnicIScsiAdaptorProfileName                                  SnmpAdminString,
    cucsVnicIScsiAddr                                                MacAddress,
    cucsVnicIScsiAdminVcon                                           SnmpAdminString,
    cucsVnicIScsiAuthProfileName                                     SnmpAdminString,
    cucsVnicIScsiBootDev                                             CucsVnicVnicBootDev,
    cucsVnicIScsiConfProfileName                                     SnmpAdminString,
    cucsVnicIScsiConfigState                                         CucsLsConfigState,
    cucsVnicIScsiEquipmentDn                                         SnmpAdminString,
    cucsVnicIScsiEthEpDn                                             SnmpAdminString,
    cucsVnicIScsiExtIPState                                          CucsVnicExternalMgmtIPMode,
    cucsVnicIScsiFltAggr                                             Unsigned64,
    cucsVnicIScsiIdentPoolName                                       SnmpAdminString,
    cucsVnicIScsiInitiatorName                                       SnmpAdminString,
    cucsVnicIScsiInstType                                            CucsVnicInstantiation,
    cucsVnicIScsiIqnIdentPoolName                                    SnmpAdminString,
    cucsVnicIScsiName                                                SnmpAdminString,
    cucsVnicIScsiNwTemplName                                         SnmpAdminString,
    cucsVnicIScsiOperAdaptorProfileName                              SnmpAdminString,
    cucsVnicIScsiOperAuthProfileName                                 SnmpAdminString,
    cucsVnicIScsiOperConfProfileName                                 SnmpAdminString,
    cucsVnicIScsiOperIqnIdentPoolName                                SnmpAdminString,
    cucsVnicIScsiOperOrder                                           Gauge32,
    cucsVnicIScsiOperSpeed                                           Gauge32,
    cucsVnicIScsiOperStatsPolicyName                                 SnmpAdminString,
    cucsVnicIScsiOperVcon                                            SnmpAdminString,
    cucsVnicIScsiOrder                                               Gauge32,
    cucsVnicIScsiOwner                                               CucsVnicConnectionOwner,
    cucsVnicIScsiPinToGroupName                                      SnmpAdminString,
    cucsVnicIScsiQosPolicyName                                       SnmpAdminString,
    cucsVnicIScsiStatsPolicyName                                     SnmpAdminString,
    cucsVnicIScsiSwitchId                                            CucsNetworkSwitchId,
    cucsVnicIScsiType                                                CucsVnicConnectionType,
    cucsVnicIScsiVnicDefType                                         CucsVnicIScsiIfDefType,
    cucsVnicIScsiVnicName                                            SnmpAdminString
}

cucsVnicIScsiInstanceId OBJECT-TYPE
    SYNTAX       CucsManagedObjectId
    MAX-ACCESS   not-accessible
    STATUS       current
    DESCRIPTION
        "Instance identifier of the managed object."
    ::= { cucsVnicIScsiEntry 1 }

cucsVnicIScsiDn OBJECT-TYPE
    SYNTAX       CucsManagedObjectDn
    MAX-ACCESS   read-only
    STATUS       current
    DESCRIPTION
        "Cisco UCS vnic:IScsi:dn managed object property"
    ::= { cucsVnicIScsiEntry 2 }

cucsVnicIScsiRn OBJECT-TYPE
    SYNTAX       SnmpAdminString
    MAX-ACCESS   read-only
    STATUS       current
    DESCRIPTION
        "Cisco UCS vnic:IScsi:rn managed object property"
    ::= { cucsVnicIScsiEntry 3 }

cucsVnicIScsiAdaptorProfileName OBJECT-TYPE
    SYNTAX       SnmpAdminString
    MAX-ACCESS   read-only
    STATUS       current
    DESCRIPTION
        "Cisco UCS vnic:IScsi:adaptorProfileName managed object property"
    ::= { cucsVnicIScsiEntry 4 }

cucsVnicIScsiAddr OBJECT-TYPE
    SYNTAX       MacAddress
    MAX-ACCESS   read-only
    STATUS       current
    DESCRIPTION
        "Cisco UCS vnic:IScsi:addr managed object property"
    ::= { cucsVnicIScsiEntry 5 }

cucsVnicIScsiAdminVcon OBJECT-TYPE
    SYNTAX       SnmpAdminString
    MAX-ACCESS   read-only
    STATUS       current
    DESCRIPTION
        "Cisco UCS vnic:IScsi:adminVcon managed object property"
    ::= { cucsVnicIScsiEntry 6 }

cucsVnicIScsiAuthProfileName OBJECT-TYPE
    SYNTAX       SnmpAdminString
    MAX-ACCESS   read-only
    STATUS       current
    DESCRIPTION
        "Cisco UCS vnic:IScsi:authProfileName managed object property"
    ::= { cucsVnicIScsiEntry 7 }

cucsVnicIScsiBootDev OBJECT-TYPE
    SYNTAX       CucsVnicVnicBootDev
    MAX-ACCESS   read-only
    STATUS       current
    DESCRIPTION
        "Cisco UCS vnic:IScsi:bootDev managed object property"
    ::= { cucsVnicIScsiEntry 8 }

cucsVnicIScsiConfProfileName OBJECT-TYPE
    SYNTAX       SnmpAdminString
    MAX-ACCESS   read-only
    STATUS       current
    DESCRIPTION
        "Cisco UCS vnic:IScsi:confProfileName managed object property"
    ::= { cucsVnicIScsiEntry 9 }

cucsVnicIScsiConfigState OBJECT-TYPE
    SYNTAX       CucsLsConfigState
    MAX-ACCESS   read-only
    STATUS       current
    DESCRIPTION
        "Cisco UCS vnic:IScsi:configState managed object property"
    ::= { cucsVnicIScsiEntry 10 }

cucsVnicIScsiEquipmentDn OBJECT-TYPE
    SYNTAX       SnmpAdminString
    MAX-ACCESS   read-only
    STATUS       current
    DESCRIPTION
        "Cisco UCS vnic:IScsi:equipmentDn managed object property"
    ::= { cucsVnicIScsiEntry 11 }

cucsVnicIScsiEthEpDn OBJECT-TYPE
    SYNTAX       SnmpAdminString
    MAX-ACCESS   read-only
    STATUS       current
    DESCRIPTION
        "Cisco UCS vnic:IScsi:ethEpDn managed object property"
    ::= { cucsVnicIScsiEntry 12 }

cucsVnicIScsiExtIPState OBJECT-TYPE
    SYNTAX       CucsVnicExternalMgmtIPMode
    MAX-ACCESS   read-only
    STATUS       current
    DESCRIPTION
        "Cisco UCS vnic:IScsi:extIPState managed object property"
    ::= { cucsVnicIScsiEntry 13 }

cucsVnicIScsiFltAggr OBJECT-TYPE
    SYNTAX       Unsigned64
    MAX-ACCESS   read-only
    STATUS       current
    DESCRIPTION
        "Cisco UCS vnic:IScsi:fltAggr managed object property"
    ::= { cucsVnicIScsiEntry 14 }

cucsVnicIScsiIdentPoolName OBJECT-TYPE
    SYNTAX       SnmpAdminString
    MAX-ACCESS   read-only
    STATUS       current
    DESCRIPTION
        "Cisco UCS vnic:IScsi:identPoolName managed object property"
    ::= { cucsVnicIScsiEntry 15 }

cucsVnicIScsiInitiatorName OBJECT-TYPE
    SYNTAX       SnmpAdminString
    MAX-ACCESS   read-only
    STATUS       current
    DESCRIPTION
        "Cisco UCS vnic:IScsi:initiatorName managed object property"
    ::= { cucsVnicIScsiEntry 16 }

cucsVnicIScsiInstType OBJECT-TYPE
    SYNTAX       CucsVnicInstantiation
    MAX-ACCESS   read-only
    STATUS       current
    DESCRIPTION
        "Cisco UCS vnic:IScsi:instType managed object property"
    ::= { cucsVnicIScsiEntry 17 }

cucsVnicIScsiIqnIdentPoolName OBJECT-TYPE
    SYNTAX       SnmpAdminString
    MAX-ACCESS   read-only
    STATUS       current
    DESCRIPTION
        "Cisco UCS vnic:IScsi:iqnIdentPoolName managed object property"
    ::= { cucsVnicIScsiEntry 18 }

cucsVnicIScsiName OBJECT-TYPE
    SYNTAX       SnmpAdminString
    MAX-ACCESS   read-only
    STATUS       current
    DESCRIPTION
        "Cisco UCS vnic:IScsi:name managed object property"
    ::= { cucsVnicIScsiEntry 19 }

cucsVnicIScsiNwTemplName OBJECT-TYPE
    SYNTAX       SnmpAdminString
    MAX-ACCESS   read-only
    STATUS       current
    DESCRIPTION
        "Cisco UCS vnic:IScsi:nwTemplName managed object property"
    ::= { cucsVnicIScsiEntry 20 }

cucsVnicIScsiOperAdaptorProfileName OBJECT-TYPE
    SYNTAX       SnmpAdminString
    MAX-ACCESS   read-only
    STATUS       current
    DESCRIPTION
        "Cisco UCS vnic:IScsi:operAdaptorProfileName managed
        object property"
    ::= { cucsVnicIScsiEntry 21 }

cucsVnicIScsiOperAuthProfileName OBJECT-TYPE
    SYNTAX       SnmpAdminString
    MAX-ACCESS   read-only
    STATUS       current
    DESCRIPTION
        "Cisco UCS vnic:IScsi:operAuthProfileName managed object property"
    ::= { cucsVnicIScsiEntry 22 }

cucsVnicIScsiOperConfProfileName OBJECT-TYPE
    SYNTAX       SnmpAdminString
    MAX-ACCESS   read-only
    STATUS       current
    DESCRIPTION
        "Cisco UCS vnic:IScsi:operConfProfileName managed object property"
    ::= { cucsVnicIScsiEntry 23 }

cucsVnicIScsiOperIqnIdentPoolName OBJECT-TYPE
    SYNTAX       SnmpAdminString
    MAX-ACCESS   read-only
    STATUS       current
    DESCRIPTION
        "Cisco UCS vnic:IScsi:operIqnIdentPoolName managed
        object property"
    ::= { cucsVnicIScsiEntry 24 }

cucsVnicIScsiOperOrder OBJECT-TYPE
    SYNTAX       Gauge32
    MAX-ACCESS   read-only
    STATUS       current
    DESCRIPTION
        "Cisco UCS vnic:IScsi:operOrder managed object property"
    ::= { cucsVnicIScsiEntry 25 }

cucsVnicIScsiOperSpeed OBJECT-TYPE
    SYNTAX       Gauge32
    MAX-ACCESS   read-only
    STATUS       current
    DESCRIPTION
        "Cisco UCS vnic:IScsi:operSpeed managed object property"
    ::= { cucsVnicIScsiEntry 27 }

cucsVnicIScsiOperStatsPolicyName OBJECT-TYPE
    SYNTAX       SnmpAdminString
    MAX-ACCESS   read-only
    STATUS       current
    DESCRIPTION
        "Cisco UCS vnic:IScsi:operStatsPolicyName managed object property"
    ::= { cucsVnicIScsiEntry 28 }

cucsVnicIScsiOperVcon OBJECT-TYPE
    SYNTAX       SnmpAdminString
    MAX-ACCESS   read-only
    STATUS       current
    DESCRIPTION
        "Cisco UCS vnic:IScsi:operVcon managed object property"
    ::= { cucsVnicIScsiEntry 29 }

cucsVnicIScsiOrder OBJECT-TYPE
    SYNTAX       Gauge32
    MAX-ACCESS   read-only
    STATUS       current
    DESCRIPTION
        "Cisco UCS vnic:IScsi:order managed object property"
    ::= { cucsVnicIScsiEntry 30 }

cucsVnicIScsiOwner OBJECT-TYPE
    SYNTAX       CucsVnicConnectionOwner
    MAX-ACCESS   read-only
    STATUS       current
    DESCRIPTION
        "Cisco UCS vnic:IScsi:owner managed object property"
    ::= { cucsVnicIScsiEntry 31 }

cucsVnicIScsiPinToGroupName OBJECT-TYPE
    SYNTAX       SnmpAdminString
    MAX-ACCESS   read-only
    STATUS       current
    DESCRIPTION
        "Cisco UCS vnic:IScsi:pinToGroupName managed object property"
    ::= { cucsVnicIScsiEntry 32 }

cucsVnicIScsiQosPolicyName OBJECT-TYPE
    SYNTAX       SnmpAdminString
    MAX-ACCESS   read-only
    STATUS       current
    DESCRIPTION
        "Cisco UCS vnic:IScsi:qosPolicyName managed object property"
    ::= { cucsVnicIScsiEntry 33 }

cucsVnicIScsiStatsPolicyName OBJECT-TYPE
    SYNTAX       SnmpAdminString
    MAX-ACCESS   read-only
    STATUS       current
    DESCRIPTION
        "Cisco UCS vnic:IScsi:statsPolicyName managed object property"
    ::= { cucsVnicIScsiEntry 34 }

cucsVnicIScsiSwitchId OBJECT-TYPE
    SYNTAX       CucsNetworkSwitchId
    MAX-ACCESS   read-only
    STATUS       current
    DESCRIPTION
        "Cisco UCS vnic:IScsi:switchId managed object property"
    ::= { cucsVnicIScsiEntry 35 }

cucsVnicIScsiType OBJECT-TYPE
    SYNTAX       CucsVnicConnectionType
    MAX-ACCESS   read-only
    STATUS       current
    DESCRIPTION
        "Cisco UCS vnic:IScsi:type managed object property"
    ::= { cucsVnicIScsiEntry 36 }

cucsVnicIScsiVnicDefType OBJECT-TYPE
    SYNTAX       CucsVnicIScsiIfDefType
    MAX-ACCESS   read-only
    STATUS       current
    DESCRIPTION
        "Cisco UCS vnic:IScsi:vnicDefType managed object property"
    ::= { cucsVnicIScsiEntry 37 }

cucsVnicIScsiVnicName OBJECT-TYPE
    SYNTAX       SnmpAdminString
    MAX-ACCESS   read-only
    STATUS       current
    DESCRIPTION
        "Cisco UCS vnic:IScsi:vnicName managed object property"
    ::= { cucsVnicIScsiEntry 38 }

cucsVnicIScsiAutoTargetIfTable OBJECT-TYPE
    SYNTAX           SEQUENCE OF CucsVnicIScsiAutoTargetIfEntry
    MAX-ACCESS       not-accessible
    STATUS           current
    DESCRIPTION
        "Cisco UCS vnic:IScsiAutoTargetIf managed object table"
    ::= { cucsVnicObjects 39 }

cucsVnicIScsiAutoTargetIfEntry OBJECT-TYPE
    SYNTAX           CucsVnicIScsiAutoTargetIfEntry
    MAX-ACCESS       not-accessible
    STATUS           current
    DESCRIPTION
        "Entry for the cucsVnicIScsiAutoTargetIfTable table."
    INDEX { cucsVnicIScsiAutoTargetIfInstanceId }
    ::= { cucsVnicIScsiAutoTargetIfTable 1 }

CucsVnicIScsiAutoTargetIfEntry ::= SEQUENCE {
    cucsVnicIScsiAutoTargetIfInstanceId                              CucsManagedObjectId,
    cucsVnicIScsiAutoTargetIfDn                                      CucsManagedObjectDn,
    cucsVnicIScsiAutoTargetIfRn                                      SnmpAdminString,
    cucsVnicIScsiAutoTargetIfDhcpVendorId                            SnmpAdminString
}

cucsVnicIScsiAutoTargetIfInstanceId OBJECT-TYPE
    SYNTAX       CucsManagedObjectId
    MAX-ACCESS   not-accessible
    STATUS       current
    DESCRIPTION
        "Instance identifier of the managed object."
    ::= { cucsVnicIScsiAutoTargetIfEntry 1 }

cucsVnicIScsiAutoTargetIfDn OBJECT-TYPE
    SYNTAX       CucsManagedObjectDn
    MAX-ACCESS   read-only
    STATUS       current
    DESCRIPTION
        "Cisco UCS vnic:IScsiAutoTargetIf:dn managed object property"
    ::= { cucsVnicIScsiAutoTargetIfEntry 2 }

cucsVnicIScsiAutoTargetIfRn OBJECT-TYPE
    SYNTAX       SnmpAdminString
    MAX-ACCESS   read-only
    STATUS       current
    DESCRIPTION
        "Cisco UCS vnic:IScsiAutoTargetIf:rn managed object property"
    ::= { cucsVnicIScsiAutoTargetIfEntry 3 }

cucsVnicIScsiAutoTargetIfDhcpVendorId OBJECT-TYPE
    SYNTAX       SnmpAdminString
    MAX-ACCESS   read-only
    STATUS       current
    DESCRIPTION
        "Cisco UCS vnic:IScsiAutoTargetIf:dhcpVendorId
        managed object property"
    ::= { cucsVnicIScsiAutoTargetIfEntry 4 }

cucsVnicIScsiNodeTable OBJECT-TYPE
    SYNTAX           SEQUENCE OF CucsVnicIScsiNodeEntry
    MAX-ACCESS       not-accessible
    STATUS           current
    DESCRIPTION
        "Cisco UCS vnic:IScsiNode managed object table"
    ::= { cucsVnicObjects 40 }

cucsVnicIScsiNodeEntry OBJECT-TYPE
    SYNTAX           CucsVnicIScsiNodeEntry
    MAX-ACCESS       not-accessible
    STATUS           current
    DESCRIPTION
        "Entry for the cucsVnicIScsiNodeTable table."
    INDEX { cucsVnicIScsiNodeInstanceId }
    ::= { cucsVnicIScsiNodeTable 1 }

CucsVnicIScsiNodeEntry ::= SEQUENCE {
    cucsVnicIScsiNodeInstanceId                                      CucsManagedObjectId,
    cucsVnicIScsiNodeDn                                              CucsManagedObjectDn,
    cucsVnicIScsiNodeRn                                              SnmpAdminString,
    cucsVnicIScsiNodeFltAggr                                         Unsigned64,
    cucsVnicIScsiNodeInitiatorName                                   SnmpAdminString
}

cucsVnicIScsiNodeInstanceId OBJECT-TYPE
    SYNTAX       CucsManagedObjectId
    MAX-ACCESS   not-accessible
    STATUS       current
    DESCRIPTION
        "Instance identifier of the managed object."
    ::= { cucsVnicIScsiNodeEntry 1 }

cucsVnicIScsiNodeDn OBJECT-TYPE
    SYNTAX       CucsManagedObjectDn
    MAX-ACCESS   read-only
    STATUS       current
    DESCRIPTION
        "Cisco UCS vnic:IScsiNode:dn managed object property"
    ::= { cucsVnicIScsiNodeEntry 2 }

cucsVnicIScsiNodeRn OBJECT-TYPE
    SYNTAX       SnmpAdminString
    MAX-ACCESS   read-only
    STATUS       current
    DESCRIPTION
        "Cisco UCS vnic:IScsiNode:rn managed object property"
    ::= { cucsVnicIScsiNodeEntry 3 }

cucsVnicIScsiNodeFltAggr OBJECT-TYPE
    SYNTAX       Unsigned64
    MAX-ACCESS   read-only
    STATUS       current
    DESCRIPTION
        "Cisco UCS vnic:IScsiNode:fltAggr managed object property"
    ::= { cucsVnicIScsiNodeEntry 4 }

cucsVnicIScsiNodeInitiatorName OBJECT-TYPE
    SYNTAX       SnmpAdminString
    MAX-ACCESS   read-only
    STATUS       current
    DESCRIPTION
        "Cisco UCS vnic:IScsiNode:initiatorName managed object property"
    ::= { cucsVnicIScsiNodeEntry 5 }

cucsVnicIScsiStaticTargetIfTable OBJECT-TYPE
    SYNTAX           SEQUENCE OF CucsVnicIScsiStaticTargetIfEntry
    MAX-ACCESS       not-accessible
    STATUS           current
    DESCRIPTION
        "Cisco UCS vnic:IScsiStaticTargetIf managed object table"
    ::= { cucsVnicObjects 41 }

cucsVnicIScsiStaticTargetIfEntry OBJECT-TYPE
    SYNTAX           CucsVnicIScsiStaticTargetIfEntry
    MAX-ACCESS       not-accessible
    STATUS           current
    DESCRIPTION
        "Entry for the cucsVnicIScsiStaticTargetIfTable table."
    INDEX { cucsVnicIScsiStaticTargetIfInstanceId }
    ::= { cucsVnicIScsiStaticTargetIfTable 1 }

CucsVnicIScsiStaticTargetIfEntry ::= SEQUENCE {
    cucsVnicIScsiStaticTargetIfInstanceId                            CucsManagedObjectId,
    cucsVnicIScsiStaticTargetIfDn                                    CucsManagedObjectDn,
    cucsVnicIScsiStaticTargetIfRn                                    SnmpAdminString,
    cucsVnicIScsiStaticTargetIfAuthProfileName                       SnmpAdminString,
    cucsVnicIScsiStaticTargetIfIpAddress                             InetAddressIPv4,
    cucsVnicIScsiStaticTargetIfName                                  SnmpAdminString,
    cucsVnicIScsiStaticTargetIfOperAuthProfileName                   SnmpAdminString,
    cucsVnicIScsiStaticTargetIfPort                                  Gauge32,
    cucsVnicIScsiStaticTargetIfPriority                              Gauge32
}

cucsVnicIScsiStaticTargetIfInstanceId OBJECT-TYPE
    SYNTAX       CucsManagedObjectId
    MAX-ACCESS   not-accessible
    STATUS       current
    DESCRIPTION
        "Instance identifier of the managed object."
    ::= { cucsVnicIScsiStaticTargetIfEntry 1 }

cucsVnicIScsiStaticTargetIfDn OBJECT-TYPE
    SYNTAX       CucsManagedObjectDn
    MAX-ACCESS   read-only
    STATUS       current
    DESCRIPTION
        "Cisco UCS vnic:IScsiStaticTargetIf:dn managed object property"
    ::= { cucsVnicIScsiStaticTargetIfEntry 2 }

cucsVnicIScsiStaticTargetIfRn OBJECT-TYPE
    SYNTAX       SnmpAdminString
    MAX-ACCESS   read-only
    STATUS       current
    DESCRIPTION
        "Cisco UCS vnic:IScsiStaticTargetIf:rn managed object property"
    ::= { cucsVnicIScsiStaticTargetIfEntry 3 }

cucsVnicIScsiStaticTargetIfAuthProfileName OBJECT-TYPE
    SYNTAX       SnmpAdminString
    MAX-ACCESS   read-only
    STATUS       current
    DESCRIPTION
        "Cisco UCS vnic:IScsiStaticTargetIf:authProfileName
        managed object property"
    ::= { cucsVnicIScsiStaticTargetIfEntry 4 }

cucsVnicIScsiStaticTargetIfIpAddress OBJECT-TYPE
    SYNTAX       InetAddressIPv4
    MAX-ACCESS   read-only
    STATUS       current
    DESCRIPTION
        "Cisco UCS vnic:IScsiStaticTargetIf:ipAddress managed
        object property"
    ::= { cucsVnicIScsiStaticTargetIfEntry 5 }

cucsVnicIScsiStaticTargetIfName OBJECT-TYPE
    SYNTAX       SnmpAdminString
    MAX-ACCESS   read-only
    STATUS       current
    DESCRIPTION
        "Cisco UCS vnic:IScsiStaticTargetIf:name managed object property"
    ::= { cucsVnicIScsiStaticTargetIfEntry 6 }

cucsVnicIScsiStaticTargetIfOperAuthProfileName OBJECT-TYPE
    SYNTAX       SnmpAdminString
    MAX-ACCESS   read-only
    STATUS       current
    DESCRIPTION
        "Cisco UCS vnic:IScsiStaticTargetIf:operAuthProfileName
        managed object property"
    ::= { cucsVnicIScsiStaticTargetIfEntry 7 }

cucsVnicIScsiStaticTargetIfPort OBJECT-TYPE
    SYNTAX       Gauge32
    MAX-ACCESS   read-only
    STATUS       current
    DESCRIPTION
        "Cisco UCS vnic:IScsiStaticTargetIf:port managed object property"
    ::= { cucsVnicIScsiStaticTargetIfEntry 8 }

cucsVnicIScsiStaticTargetIfPriority OBJECT-TYPE
    SYNTAX       Gauge32
    MAX-ACCESS   read-only
    STATUS       current
    DESCRIPTION
        "Cisco UCS vnic:IScsiStaticTargetIf:priority managed
        object property"
    ::= { cucsVnicIScsiStaticTargetIfEntry 9 }

cucsVnicInternalProfileTable OBJECT-TYPE
    SYNTAX           SEQUENCE OF CucsVnicInternalProfileEntry
    MAX-ACCESS       not-accessible
    STATUS           current
    DESCRIPTION
        "Cisco UCS vnic:InternalProfile managed object table"
    ::= { cucsVnicObjects 42 }

cucsVnicInternalProfileEntry OBJECT-TYPE
    SYNTAX           CucsVnicInternalProfileEntry
    MAX-ACCESS       not-accessible
    STATUS           current
    DESCRIPTION
        "Entry for the cucsVnicInternalProfileTable table."
    INDEX { cucsVnicInternalProfileInstanceId }
    ::= { cucsVnicInternalProfileTable 1 }

CucsVnicInternalProfileEntry ::= SEQUENCE {
    cucsVnicInternalProfileInstanceId                                CucsManagedObjectId,
    cucsVnicInternalProfileDn                                        CucsManagedObjectDn,
    cucsVnicInternalProfileRn                                        SnmpAdminString,
    cucsVnicInternalProfileDescr                                     SnmpAdminString,
    cucsVnicInternalProfileIntId                                     SnmpAdminString,
    cucsVnicInternalProfileMaxPorts                                  Gauge32,
    cucsVnicInternalProfileName                                      SnmpAdminString
}

cucsVnicInternalProfileInstanceId OBJECT-TYPE
    SYNTAX       CucsManagedObjectId
    MAX-ACCESS   not-accessible
    STATUS       current
    DESCRIPTION
        "Instance identifier of the managed object."
    ::= { cucsVnicInternalProfileEntry 1 }

cucsVnicInternalProfileDn OBJECT-TYPE
    SYNTAX       CucsManagedObjectDn
    MAX-ACCESS   read-only
    STATUS       current
    DESCRIPTION
        "Cisco UCS vnic:InternalProfile:dn managed object property"
    ::= { cucsVnicInternalProfileEntry 2 }

cucsVnicInternalProfileRn OBJECT-TYPE
    SYNTAX       SnmpAdminString
    MAX-ACCESS   read-only
    STATUS       current
    DESCRIPTION
        "Cisco UCS vnic:InternalProfile:rn managed object property"
    ::= { cucsVnicInternalProfileEntry 3 }

cucsVnicInternalProfileDescr OBJECT-TYPE
    SYNTAX       SnmpAdminString
    MAX-ACCESS   read-only
    STATUS       current
    DESCRIPTION
        "Cisco UCS vnic:InternalProfile:descr managed object property"
    ::= { cucsVnicInternalProfileEntry 4 }

cucsVnicInternalProfileIntId OBJECT-TYPE
    SYNTAX       SnmpAdminString
    MAX-ACCESS   read-only
    STATUS       current
    DESCRIPTION
        "Cisco UCS vnic:InternalProfile:intId managed object property"
    ::= { cucsVnicInternalProfileEntry 5 }

cucsVnicInternalProfileMaxPorts OBJECT-TYPE
    SYNTAX       Gauge32
    MAX-ACCESS   read-only
    STATUS       current
    DESCRIPTION
        "Cisco UCS vnic:InternalProfile:maxPorts managed object property"
    ::= { cucsVnicInternalProfileEntry 6 }

cucsVnicInternalProfileName OBJECT-TYPE
    SYNTAX       SnmpAdminString
    MAX-ACCESS   read-only
    STATUS       current
    DESCRIPTION
        "Cisco UCS vnic:InternalProfile:name managed object property"
    ::= { cucsVnicInternalProfileEntry 7 }

cucsVnicIpV4PooledAddrTable OBJECT-TYPE
    SYNTAX           SEQUENCE OF CucsVnicIpV4PooledAddrEntry
    MAX-ACCESS       not-accessible
    STATUS           current
    DESCRIPTION
        "Cisco UCS vnic:IpV4PooledAddr managed object table"
    ::= { cucsVnicObjects 20 }

cucsVnicIpV4PooledAddrEntry OBJECT-TYPE
    SYNTAX           CucsVnicIpV4PooledAddrEntry
    MAX-ACCESS       not-accessible
    STATUS           current
    DESCRIPTION
        "Entry for the cucsVnicIpV4PooledAddrTable table."
    INDEX { cucsVnicIpV4PooledAddrInstanceId }
    ::= { cucsVnicIpV4PooledAddrTable 1 }

CucsVnicIpV4PooledAddrEntry ::= SEQUENCE {
    cucsVnicIpV4PooledAddrInstanceId                                 CucsManagedObjectId,
    cucsVnicIpV4PooledAddrDn                                         CucsManagedObjectDn,
    cucsVnicIpV4PooledAddrRn                                         SnmpAdminString,
    cucsVnicIpV4PooledAddrAddr                                       InetAddressIPv4,
    cucsVnicIpV4PooledAddrDefGw                                      InetAddressIPv4,
    cucsVnicIpV4PooledAddrName                                       SnmpAdminString,
    cucsVnicIpV4PooledAddrSubnet                                     InetAddressIPv4
}

cucsVnicIpV4PooledAddrInstanceId OBJECT-TYPE
    SYNTAX       CucsManagedObjectId
    MAX-ACCESS   not-accessible
    STATUS       current
    DESCRIPTION
        "Instance identifier of the managed object."
    ::= { cucsVnicIpV4PooledAddrEntry 1 }

cucsVnicIpV4PooledAddrDn OBJECT-TYPE
    SYNTAX       CucsManagedObjectDn
    MAX-ACCESS   read-only
    STATUS       current
    DESCRIPTION
        "Cisco UCS vnic:IpV4PooledAddr:dn managed object property"
    ::= { cucsVnicIpV4PooledAddrEntry 2 }

cucsVnicIpV4PooledAddrRn OBJECT-TYPE
    SYNTAX       SnmpAdminString
    MAX-ACCESS   read-only
    STATUS       current
    DESCRIPTION
        "Cisco UCS vnic:IpV4PooledAddr:rn managed object property"
    ::= { cucsVnicIpV4PooledAddrEntry 3 }

cucsVnicIpV4PooledAddrAddr OBJECT-TYPE
    SYNTAX       InetAddressIPv4
    MAX-ACCESS   read-only
    STATUS       current
    DESCRIPTION
        "Cisco UCS vnic:IpV4PooledAddr:addr managed object property"
    ::= { cucsVnicIpV4PooledAddrEntry 4 }

cucsVnicIpV4PooledAddrDefGw OBJECT-TYPE
    SYNTAX       InetAddressIPv4
    MAX-ACCESS   read-only
    STATUS       current
    DESCRIPTION
        "Cisco UCS vnic:IpV4PooledAddr:defGw managed object property"
    ::= { cucsVnicIpV4PooledAddrEntry 5 }

cucsVnicIpV4PooledAddrName OBJECT-TYPE
    SYNTAX       SnmpAdminString
    MAX-ACCESS   read-only
    STATUS       current
    DESCRIPTION
        "Cisco UCS vnic:IpV4PooledAddr:name managed object property"
    ::= { cucsVnicIpV4PooledAddrEntry 6 }

cucsVnicIpV4PooledAddrSubnet OBJECT-TYPE
    SYNTAX       InetAddressIPv4
    MAX-ACCESS   read-only
    STATUS       current
    DESCRIPTION
        "Cisco UCS vnic:IpV4PooledAddr:subnet managed object property"
    ::= { cucsVnicIpV4PooledAddrEntry 7 }

cucsVnicIpV4ProfDerivedAddrTable OBJECT-TYPE
    SYNTAX           SEQUENCE OF CucsVnicIpV4ProfDerivedAddrEntry
    MAX-ACCESS       not-accessible
    STATUS           current
    DESCRIPTION
        "Cisco UCS vnic:IpV4ProfDerivedAddr managed object table"
    ::= { cucsVnicObjects 21 }

cucsVnicIpV4ProfDerivedAddrEntry OBJECT-TYPE
    SYNTAX           CucsVnicIpV4ProfDerivedAddrEntry
    MAX-ACCESS       not-accessible
    STATUS           current
    DESCRIPTION
        "Entry for the cucsVnicIpV4ProfDerivedAddrTable table."
    INDEX { cucsVnicIpV4ProfDerivedAddrInstanceId }
    ::= { cucsVnicIpV4ProfDerivedAddrTable 1 }

CucsVnicIpV4ProfDerivedAddrEntry ::= SEQUENCE {
    cucsVnicIpV4ProfDerivedAddrInstanceId                            CucsManagedObjectId,
    cucsVnicIpV4ProfDerivedAddrDn                                    CucsManagedObjectDn,
    cucsVnicIpV4ProfDerivedAddrRn                                    SnmpAdminString,
    cucsVnicIpV4ProfDerivedAddrAddr                                  InetAddressIPv4,
    cucsVnicIpV4ProfDerivedAddrDefGw                                 InetAddressIPv4,
    cucsVnicIpV4ProfDerivedAddrSubnet                                InetAddressIPv4
}

cucsVnicIpV4ProfDerivedAddrInstanceId OBJECT-TYPE
    SYNTAX       CucsManagedObjectId
    MAX-ACCESS   not-accessible
    STATUS       current
    DESCRIPTION
        "Instance identifier of the managed object."
    ::= { cucsVnicIpV4ProfDerivedAddrEntry 1 }

cucsVnicIpV4ProfDerivedAddrDn OBJECT-TYPE
    SYNTAX       CucsManagedObjectDn
    MAX-ACCESS   read-only
    STATUS       current
    DESCRIPTION
        "Cisco UCS vnic:IpV4ProfDerivedAddr:dn managed object property"
    ::= { cucsVnicIpV4ProfDerivedAddrEntry 2 }

cucsVnicIpV4ProfDerivedAddrRn OBJECT-TYPE
    SYNTAX       SnmpAdminString
    MAX-ACCESS   read-only
    STATUS       current
    DESCRIPTION
        "Cisco UCS vnic:IpV4ProfDerivedAddr:rn managed object property"
    ::= { cucsVnicIpV4ProfDerivedAddrEntry 3 }

cucsVnicIpV4ProfDerivedAddrAddr OBJECT-TYPE
    SYNTAX       InetAddressIPv4
    MAX-ACCESS   read-only
    STATUS       current
    DESCRIPTION
        "Cisco UCS vnic:IpV4ProfDerivedAddr:addr managed object property"
    ::= { cucsVnicIpV4ProfDerivedAddrEntry 4 }

cucsVnicIpV4ProfDerivedAddrDefGw OBJECT-TYPE
    SYNTAX       InetAddressIPv4
    MAX-ACCESS   read-only
    STATUS       current
    DESCRIPTION
        "Cisco UCS vnic:IpV4ProfDerivedAddr:defGw managed object property"
    ::= { cucsVnicIpV4ProfDerivedAddrEntry 5 }

cucsVnicIpV4ProfDerivedAddrSubnet OBJECT-TYPE
    SYNTAX       InetAddressIPv4
    MAX-ACCESS   read-only
    STATUS       current
    DESCRIPTION
        "Cisco UCS vnic:IpV4ProfDerivedAddr:subnet managed
        object property"
    ::= { cucsVnicIpV4ProfDerivedAddrEntry 6 }

cucsVnicIpV4StaticAddrTable OBJECT-TYPE
    SYNTAX           SEQUENCE OF CucsVnicIpV4StaticAddrEntry
    MAX-ACCESS       not-accessible
    STATUS           current
    DESCRIPTION
        "Cisco UCS vnic:IpV4StaticAddr managed object table"
    ::= { cucsVnicObjects 22 }

cucsVnicIpV4StaticAddrEntry OBJECT-TYPE
    SYNTAX           CucsVnicIpV4StaticAddrEntry
    MAX-ACCESS       not-accessible
    STATUS           current
    DESCRIPTION
        "Entry for the cucsVnicIpV4StaticAddrTable table."
    INDEX { cucsVnicIpV4StaticAddrInstanceId }
    ::= { cucsVnicIpV4StaticAddrTable 1 }

CucsVnicIpV4StaticAddrEntry ::= SEQUENCE {
    cucsVnicIpV4StaticAddrInstanceId                                 CucsManagedObjectId,
    cucsVnicIpV4StaticAddrDn                                         CucsManagedObjectDn,
    cucsVnicIpV4StaticAddrRn                                         SnmpAdminString,
    cucsVnicIpV4StaticAddrAddr                                       InetAddressIPv4,
    cucsVnicIpV4StaticAddrDefGw                                      InetAddressIPv4,
    cucsVnicIpV4StaticAddrSubnet                                     InetAddressIPv4
}

cucsVnicIpV4StaticAddrInstanceId OBJECT-TYPE
    SYNTAX       CucsManagedObjectId
    MAX-ACCESS   not-accessible
    STATUS       current
    DESCRIPTION
        "Instance identifier of the managed object."
    ::= { cucsVnicIpV4StaticAddrEntry 1 }

cucsVnicIpV4StaticAddrDn OBJECT-TYPE
    SYNTAX       CucsManagedObjectDn
    MAX-ACCESS   read-only
    STATUS       current
    DESCRIPTION
        "Cisco UCS vnic:IpV4StaticAddr:dn managed object property"
    ::= { cucsVnicIpV4StaticAddrEntry 2 }

cucsVnicIpV4StaticAddrRn OBJECT-TYPE
    SYNTAX       SnmpAdminString
    MAX-ACCESS   read-only
    STATUS       current
    DESCRIPTION
        "Cisco UCS vnic:IpV4StaticAddr:rn managed object property"
    ::= { cucsVnicIpV4StaticAddrEntry 3 }

cucsVnicIpV4StaticAddrAddr OBJECT-TYPE
    SYNTAX       InetAddressIPv4
    MAX-ACCESS   read-only
    STATUS       current
    DESCRIPTION
        "Cisco UCS vnic:IpV4StaticAddr:addr managed object property"
    ::= { cucsVnicIpV4StaticAddrEntry 4 }

cucsVnicIpV4StaticAddrDefGw OBJECT-TYPE
    SYNTAX       InetAddressIPv4
    MAX-ACCESS   read-only
    STATUS       current
    DESCRIPTION
        "Cisco UCS vnic:IpV4StaticAddr:defGw managed object property"
    ::= { cucsVnicIpV4StaticAddrEntry 5 }

cucsVnicIpV4StaticAddrSubnet OBJECT-TYPE
    SYNTAX       InetAddressIPv4
    MAX-ACCESS   read-only
    STATUS       current
    DESCRIPTION
        "Cisco UCS vnic:IpV4StaticAddr:subnet managed object property"
    ::= { cucsVnicIpV4StaticAddrEntry 6 }

cucsVnicIpcTable OBJECT-TYPE
    SYNTAX           SEQUENCE OF CucsVnicIpcEntry
    MAX-ACCESS       not-accessible
    STATUS           current
    DESCRIPTION
        "Cisco UCS vnic:Ipc managed object table"
    ::= { cucsVnicObjects 23 }

cucsVnicIpcEntry OBJECT-TYPE
    SYNTAX           CucsVnicIpcEntry
    MAX-ACCESS       not-accessible
    STATUS           current
    DESCRIPTION
        "Entry for the cucsVnicIpcTable table."
    INDEX { cucsVnicIpcInstanceId }
    ::= { cucsVnicIpcTable 1 }

CucsVnicIpcEntry ::= SEQUENCE {
    cucsVnicIpcInstanceId                                            CucsManagedObjectId,
    cucsVnicIpcDn                                                    CucsManagedObjectDn,
    cucsVnicIpcRn                                                    SnmpAdminString,
    cucsVnicIpcAdaptorProfileName                                    SnmpAdminString,
    cucsVnicIpcAddr                                                  MacAddress,
    cucsVnicIpcAdminVcon                                             SnmpAdminString,
    cucsVnicIpcBootDev                                               CucsVnicVnicBootDev,
    cucsVnicIpcConfigState                                           CucsLsConfigState,
    cucsVnicIpcEquipmentDn                                           SnmpAdminString,
    cucsVnicIpcIdentPoolName                                         SnmpAdminString,
    cucsVnicIpcInstType                                              CucsVnicInstantiation,
    cucsVnicIpcMtu                                                   Gauge32,
    cucsVnicIpcName                                                  SnmpAdminString,
    cucsVnicIpcNwCtrlPolicyName                                      SnmpAdminString,
    cucsVnicIpcNwTemplName                                           SnmpAdminString,
    cucsVnicIpcOperAdaptorProfileName                                SnmpAdminString,
    cucsVnicIpcOperIdentPoolName                                     SnmpAdminString,
    cucsVnicIpcOperNwCtrlPolicyName                                  SnmpAdminString,
    cucsVnicIpcOperNwTemplName                                       SnmpAdminString,
    cucsVnicIpcOperOrder                                             Gauge32,
    cucsVnicIpcOperQosPolicyName                                     SnmpAdminString,
    cucsVnicIpcOperSpeed                                             Gauge32,
    cucsVnicIpcOperStatsPolicyName                                   SnmpAdminString,
    cucsVnicIpcOperVcon                                              SnmpAdminString,
    cucsVnicIpcOrder                                                 Gauge32,
    cucsVnicIpcOwner                                                 CucsVnicConnectionOwner,
    cucsVnicIpcPinToGroupName                                        SnmpAdminString,
    cucsVnicIpcQosPolicyName                                         SnmpAdminString,
    cucsVnicIpcStatsPolicyName                                       SnmpAdminString,
    cucsVnicIpcSwitchId                                              CucsVnicEtherBaseSwitchId,
    cucsVnicIpcType                                                  CucsVnicIpcType,
    cucsVnicIpcOperPinToGroupName                                    SnmpAdminString
}

cucsVnicIpcInstanceId OBJECT-TYPE
    SYNTAX       CucsManagedObjectId
    MAX-ACCESS   not-accessible
    STATUS       current
    DESCRIPTION
        "Instance identifier of the managed object."
    ::= { cucsVnicIpcEntry 1 }

cucsVnicIpcDn OBJECT-TYPE
    SYNTAX       CucsManagedObjectDn
    MAX-ACCESS   read-only
    STATUS       current
    DESCRIPTION
        "Cisco UCS vnic:Ipc:dn managed object property"
    ::= { cucsVnicIpcEntry 2 }

cucsVnicIpcRn OBJECT-TYPE
    SYNTAX       SnmpAdminString
    MAX-ACCESS   read-only
    STATUS       current
    DESCRIPTION
        "Cisco UCS vnic:Ipc:rn managed object property"
    ::= { cucsVnicIpcEntry 3 }

cucsVnicIpcAdaptorProfileName OBJECT-TYPE
    SYNTAX       SnmpAdminString
    MAX-ACCESS   read-only
    STATUS       current
    DESCRIPTION
        "Cisco UCS vnic:Ipc:adaptorProfileName managed object property"
    ::= { cucsVnicIpcEntry 4 }

cucsVnicIpcAddr OBJECT-TYPE
    SYNTAX       MacAddress
    MAX-ACCESS   read-only
    STATUS       current
    DESCRIPTION
        "Cisco UCS vnic:Ipc:addr managed object property"
    ::= { cucsVnicIpcEntry 5 }

cucsVnicIpcAdminVcon OBJECT-TYPE
    SYNTAX       SnmpAdminString
    MAX-ACCESS   read-only
    STATUS       current
    DESCRIPTION
        "Cisco UCS vnic:Ipc:adminVcon managed object property"
    ::= { cucsVnicIpcEntry 6 }

cucsVnicIpcBootDev OBJECT-TYPE
    SYNTAX       CucsVnicVnicBootDev
    MAX-ACCESS   read-only
    STATUS       current
    DESCRIPTION
        "Cisco UCS vnic:Ipc:bootDev managed object property"
    ::= { cucsVnicIpcEntry 7 }

cucsVnicIpcConfigState OBJECT-TYPE
    SYNTAX       CucsLsConfigState
    MAX-ACCESS   read-only
    STATUS       current
    DESCRIPTION
        "Cisco UCS vnic:Ipc:configState managed object property"
    ::= { cucsVnicIpcEntry 8 }

cucsVnicIpcEquipmentDn OBJECT-TYPE
    SYNTAX       SnmpAdminString
    MAX-ACCESS   read-only
    STATUS       current
    DESCRIPTION
        "Cisco UCS vnic:Ipc:equipmentDn managed object property"
    ::= { cucsVnicIpcEntry 9 }

cucsVnicIpcIdentPoolName OBJECT-TYPE
    SYNTAX       SnmpAdminString
    MAX-ACCESS   read-only
    STATUS       current
    DESCRIPTION
        "Cisco UCS vnic:Ipc:identPoolName managed object property"
    ::= { cucsVnicIpcEntry 10 }

cucsVnicIpcInstType OBJECT-TYPE
    SYNTAX       CucsVnicInstantiation
    MAX-ACCESS   read-only
    STATUS       current
    DESCRIPTION
        "Cisco UCS vnic:Ipc:instType managed object property"
    ::= { cucsVnicIpcEntry 11 }

cucsVnicIpcMtu OBJECT-TYPE
    SYNTAX       Gauge32
    MAX-ACCESS   read-only
    STATUS       current
    DESCRIPTION
        "Cisco UCS vnic:Ipc:mtu managed object property"
    ::= { cucsVnicIpcEntry 12 }

cucsVnicIpcName OBJECT-TYPE
    SYNTAX       SnmpAdminString
    MAX-ACCESS   read-only
    STATUS       current
    DESCRIPTION
        "Cisco UCS vnic:Ipc:name managed object property"
    ::= { cucsVnicIpcEntry 13 }

cucsVnicIpcNwCtrlPolicyName OBJECT-TYPE
    SYNTAX       SnmpAdminString
    MAX-ACCESS   read-only
    STATUS       current
    DESCRIPTION
        "Cisco UCS vnic:Ipc:nwCtrlPolicyName managed object property"
    ::= { cucsVnicIpcEntry 14 }

cucsVnicIpcNwTemplName OBJECT-TYPE
    SYNTAX       SnmpAdminString
    MAX-ACCESS   read-only
    STATUS       current
    DESCRIPTION
        "Cisco UCS vnic:Ipc:nwTemplName managed object property"
    ::= { cucsVnicIpcEntry 15 }

cucsVnicIpcOperAdaptorProfileName OBJECT-TYPE
    SYNTAX       SnmpAdminString
    MAX-ACCESS   read-only
    STATUS       current
    DESCRIPTION
        "Cisco UCS vnic:Ipc:operAdaptorProfileName managed
        object property"
    ::= { cucsVnicIpcEntry 16 }

cucsVnicIpcOperIdentPoolName OBJECT-TYPE
    SYNTAX       SnmpAdminString
    MAX-ACCESS   read-only
    STATUS       current
    DESCRIPTION
        "Cisco UCS vnic:Ipc:operIdentPoolName managed object property"
    ::= { cucsVnicIpcEntry 17 }

cucsVnicIpcOperNwCtrlPolicyName OBJECT-TYPE
    SYNTAX       SnmpAdminString
    MAX-ACCESS   read-only
    STATUS       current
    DESCRIPTION
        "Cisco UCS vnic:Ipc:operNwCtrlPolicyName managed object property"
    ::= { cucsVnicIpcEntry 18 }

cucsVnicIpcOperNwTemplName OBJECT-TYPE
    SYNTAX       SnmpAdminString
    MAX-ACCESS   read-only
    STATUS       current
    DESCRIPTION
        "Cisco UCS vnic:Ipc:operNwTemplName managed object property"
    ::= { cucsVnicIpcEntry 19 }

cucsVnicIpcOperOrder OBJECT-TYPE
    SYNTAX       Gauge32
    MAX-ACCESS   read-only
    STATUS       current
    DESCRIPTION
        "Cisco UCS vnic:Ipc:operOrder managed object property"
    ::= { cucsVnicIpcEntry 20 }

cucsVnicIpcOperQosPolicyName OBJECT-TYPE
    SYNTAX       SnmpAdminString
    MAX-ACCESS   read-only
    STATUS       current
    DESCRIPTION
        "Cisco UCS vnic:Ipc:operQosPolicyName managed object property"
    ::= { cucsVnicIpcEntry 21 }

cucsVnicIpcOperSpeed OBJECT-TYPE
    SYNTAX       Gauge32
    MAX-ACCESS   read-only
    STATUS       current
    DESCRIPTION
        "Cisco UCS vnic:Ipc:operSpeed managed object property"
    ::= { cucsVnicIpcEntry 22 }

cucsVnicIpcOperStatsPolicyName OBJECT-TYPE
    SYNTAX       SnmpAdminString
    MAX-ACCESS   read-only
    STATUS       current
    DESCRIPTION
        "Cisco UCS vnic:Ipc:operStatsPolicyName managed object property"
    ::= { cucsVnicIpcEntry 23 }

cucsVnicIpcOperVcon OBJECT-TYPE
    SYNTAX       SnmpAdminString
    MAX-ACCESS   read-only
    STATUS       current
    DESCRIPTION
        "Cisco UCS vnic:Ipc:operVcon managed object property"
    ::= { cucsVnicIpcEntry 24 }

cucsVnicIpcOrder OBJECT-TYPE
    SYNTAX       Gauge32
    MAX-ACCESS   read-only
    STATUS       current
    DESCRIPTION
        "Cisco UCS vnic:Ipc:order managed object property"
    ::= { cucsVnicIpcEntry 25 }

cucsVnicIpcOwner OBJECT-TYPE
    SYNTAX       CucsVnicConnectionOwner
    MAX-ACCESS   read-only
    STATUS       current
    DESCRIPTION
        "Cisco UCS vnic:Ipc:owner managed object property"
    ::= { cucsVnicIpcEntry 26 }

cucsVnicIpcPinToGroupName OBJECT-TYPE
    SYNTAX       SnmpAdminString
    MAX-ACCESS   read-only
    STATUS       current
    DESCRIPTION
        "Cisco UCS vnic:Ipc:pinToGroupName managed object property"
    ::= { cucsVnicIpcEntry 27 }

cucsVnicIpcQosPolicyName OBJECT-TYPE
    SYNTAX       SnmpAdminString
    MAX-ACCESS   read-only
    STATUS       current
    DESCRIPTION
        "Cisco UCS vnic:Ipc:qosPolicyName managed object property"
    ::= { cucsVnicIpcEntry 28 }

cucsVnicIpcStatsPolicyName OBJECT-TYPE
    SYNTAX       SnmpAdminString
    MAX-ACCESS   read-only
    STATUS       current
    DESCRIPTION
        "Cisco UCS vnic:Ipc:statsPolicyName managed object property"
    ::= { cucsVnicIpcEntry 29 }

cucsVnicIpcSwitchId OBJECT-TYPE
    SYNTAX       CucsVnicEtherBaseSwitchId
    MAX-ACCESS   read-only
    STATUS       current
    DESCRIPTION
        "Cisco UCS vnic:Ipc:switchId managed object property"
    ::= { cucsVnicIpcEntry 30 }

cucsVnicIpcType OBJECT-TYPE
    SYNTAX       CucsVnicIpcType
    MAX-ACCESS   read-only
    STATUS       current
    DESCRIPTION
        "Cisco UCS vnic:Ipc:type managed object property"
    ::= { cucsVnicIpcEntry 31 }

cucsVnicIpcOperPinToGroupName OBJECT-TYPE
    SYNTAX       SnmpAdminString
    MAX-ACCESS   read-only
    STATUS       current
    DESCRIPTION
        "Cisco UCS vnic:Ipc:operPinToGroupName managed object property"
    ::= { cucsVnicIpcEntry 32 }

cucsVnicIpcIfTable OBJECT-TYPE
    SYNTAX           SEQUENCE OF CucsVnicIpcIfEntry
    MAX-ACCESS       not-accessible
    STATUS           current
    DESCRIPTION
        "Cisco UCS vnic:IpcIf managed object table"
    ::= { cucsVnicObjects 24 }

cucsVnicIpcIfEntry OBJECT-TYPE
    SYNTAX           CucsVnicIpcIfEntry
    MAX-ACCESS       not-accessible
    STATUS           current
    DESCRIPTION
        "Entry for the cucsVnicIpcIfTable table."
    INDEX { cucsVnicIpcIfInstanceId }
    ::= { cucsVnicIpcIfTable 1 }

CucsVnicIpcIfEntry ::= SEQUENCE {
    cucsVnicIpcIfInstanceId                                          CucsManagedObjectId,
    cucsVnicIpcIfDn                                                  CucsManagedObjectDn,
    cucsVnicIpcIfRn                                                  SnmpAdminString,
    cucsVnicIpcIfAddr                                                MacAddress,
    cucsVnicIpcIfDefaultNet                                          TruthValue,
    cucsVnicIpcIfName                                                SnmpAdminString,
    cucsVnicIpcIfOperState                                           CucsVnicIfOperState,
    cucsVnicIpcIfOwner                                               CucsVnicConnectionOwner,
    cucsVnicIpcIfSwitchId                                            CucsVnicL2IfSwitchId,
    cucsVnicIpcIfType                                                CucsVnicAIpcIfType,
    cucsVnicIpcIfVnet                                                Gauge32
}

cucsVnicIpcIfInstanceId OBJECT-TYPE
    SYNTAX       CucsManagedObjectId
    MAX-ACCESS   not-accessible
    STATUS       current
    DESCRIPTION
        "Instance identifier of the managed object."
    ::= { cucsVnicIpcIfEntry 1 }

cucsVnicIpcIfDn OBJECT-TYPE
    SYNTAX       CucsManagedObjectDn
    MAX-ACCESS   read-only
    STATUS       current
    DESCRIPTION
        "Cisco UCS vnic:IpcIf:dn managed object property"
    ::= { cucsVnicIpcIfEntry 2 }

cucsVnicIpcIfRn OBJECT-TYPE
    SYNTAX       SnmpAdminString
    MAX-ACCESS   read-only
    STATUS       current
    DESCRIPTION
        "Cisco UCS vnic:IpcIf:rn managed object property"
    ::= { cucsVnicIpcIfEntry 3 }

cucsVnicIpcIfAddr OBJECT-TYPE
    SYNTAX       MacAddress
    MAX-ACCESS   read-only
    STATUS       current
    DESCRIPTION
        "Cisco UCS vnic:IpcIf:addr managed object property"
    ::= { cucsVnicIpcIfEntry 4 }

cucsVnicIpcIfDefaultNet OBJECT-TYPE
    SYNTAX       TruthValue
    MAX-ACCESS   read-only
    STATUS       current
    DESCRIPTION
        "Cisco UCS vnic:IpcIf:defaultNet managed object property"
    ::= { cucsVnicIpcIfEntry 5 }

cucsVnicIpcIfName OBJECT-TYPE
    SYNTAX       SnmpAdminString
    MAX-ACCESS   read-only
    STATUS       current
    DESCRIPTION
        "Cisco UCS vnic:IpcIf:name managed object property"
    ::= { cucsVnicIpcIfEntry 6 }

cucsVnicIpcIfOperState OBJECT-TYPE
    SYNTAX       CucsVnicIfOperState
    MAX-ACCESS   read-only
    STATUS       current
    DESCRIPTION
        "Cisco UCS vnic:IpcIf:operState managed object property"
    ::= { cucsVnicIpcIfEntry 7 }

cucsVnicIpcIfOwner OBJECT-TYPE
    SYNTAX       CucsVnicConnectionOwner
    MAX-ACCESS   read-only
    STATUS       current
    DESCRIPTION
        "Cisco UCS vnic:IpcIf:owner managed object property"
    ::= { cucsVnicIpcIfEntry 8 }

cucsVnicIpcIfSwitchId OBJECT-TYPE
    SYNTAX       CucsVnicL2IfSwitchId
    MAX-ACCESS   read-only
    STATUS       current
    DESCRIPTION
        "Cisco UCS vnic:IpcIf:switchId managed object property"
    ::= { cucsVnicIpcIfEntry 9 }

cucsVnicIpcIfType OBJECT-TYPE
    SYNTAX       CucsVnicAIpcIfType
    MAX-ACCESS   read-only
    STATUS       current
    DESCRIPTION
        "Cisco UCS vnic:IpcIf:type managed object property"
    ::= { cucsVnicIpcIfEntry 10 }

cucsVnicIpcIfVnet OBJECT-TYPE
    SYNTAX       Gauge32
    MAX-ACCESS   read-only
    STATUS       current
    DESCRIPTION
        "Cisco UCS vnic:IpcIf:vnet managed object property"
    ::= { cucsVnicIpcIfEntry 11 }

cucsVnicLanConnTemplTable OBJECT-TYPE
    SYNTAX           SEQUENCE OF CucsVnicLanConnTemplEntry
    MAX-ACCESS       not-accessible
    STATUS           current
    DESCRIPTION
        "Cisco UCS vnic:LanConnTempl managed object table"
    ::= { cucsVnicObjects 25 }

cucsVnicLanConnTemplEntry OBJECT-TYPE
    SYNTAX           CucsVnicLanConnTemplEntry
    MAX-ACCESS       not-accessible
    STATUS           current
    DESCRIPTION
        "Entry for the cucsVnicLanConnTemplTable table."
    INDEX { cucsVnicLanConnTemplInstanceId }
    ::= { cucsVnicLanConnTemplTable 1 }

CucsVnicLanConnTemplEntry ::= SEQUENCE {
    cucsVnicLanConnTemplInstanceId                                   CucsManagedObjectId,
    cucsVnicLanConnTemplDn                                           CucsManagedObjectDn,
    cucsVnicLanConnTemplRn                                           SnmpAdminString,
    cucsVnicLanConnTemplDescr                                        SnmpAdminString,
    cucsVnicLanConnTemplIdentPoolName                                SnmpAdminString,
    cucsVnicLanConnTemplIntId                                        SnmpAdminString,
    cucsVnicLanConnTemplMtu                                          Gauge32,
    cucsVnicLanConnTemplName                                         SnmpAdminString,
    cucsVnicLanConnTemplNwCtrlPolicyName                             SnmpAdminString,
    cucsVnicLanConnTemplOperIdentPoolName                            SnmpAdminString,
    cucsVnicLanConnTemplOperNwCtrlPolicyName                         SnmpAdminString,
    cucsVnicLanConnTemplOperQosPolicyName                            SnmpAdminString,
    cucsVnicLanConnTemplOperStatsPolicyName                          SnmpAdminString,
    cucsVnicLanConnTemplPinToGroupName                               SnmpAdminString,
    cucsVnicLanConnTemplQosPolicyName                                SnmpAdminString,
    cucsVnicLanConnTemplStatsPolicyName                              SnmpAdminString,
    cucsVnicLanConnTemplSwitchId                                     CucsVnicLanConnTemplSwitchId,
    cucsVnicLanConnTemplTarget                                       CucsVnicTemplateTarget,
    cucsVnicLanConnTemplTemplType                                    CucsVnicTemplateType
}

cucsVnicLanConnTemplInstanceId OBJECT-TYPE
    SYNTAX       CucsManagedObjectId
    MAX-ACCESS   not-accessible
    STATUS       current
    DESCRIPTION
        "Instance identifier of the managed object."
    ::= { cucsVnicLanConnTemplEntry 1 }

cucsVnicLanConnTemplDn OBJECT-TYPE
    SYNTAX       CucsManagedObjectDn
    MAX-ACCESS   read-only
    STATUS       current
    DESCRIPTION
        "Cisco UCS vnic:LanConnTempl:dn managed object property"
    ::= { cucsVnicLanConnTemplEntry 2 }

cucsVnicLanConnTemplRn OBJECT-TYPE
    SYNTAX       SnmpAdminString
    MAX-ACCESS   read-only
    STATUS       current
    DESCRIPTION
        "Cisco UCS vnic:LanConnTempl:rn managed object property"
    ::= { cucsVnicLanConnTemplEntry 3 }

cucsVnicLanConnTemplDescr OBJECT-TYPE
    SYNTAX       SnmpAdminString
    MAX-ACCESS   read-only
    STATUS       current
    DESCRIPTION
        "Cisco UCS vnic:LanConnTempl:descr managed object property"
    ::= { cucsVnicLanConnTemplEntry 4 }

cucsVnicLanConnTemplIdentPoolName OBJECT-TYPE
    SYNTAX       SnmpAdminString
    MAX-ACCESS   read-only
    STATUS       current
    DESCRIPTION
        "Cisco UCS vnic:LanConnTempl:identPoolName managed
        object property"
    ::= { cucsVnicLanConnTemplEntry 5 }

cucsVnicLanConnTemplIntId OBJECT-TYPE
    SYNTAX       SnmpAdminString
    MAX-ACCESS   read-only
    STATUS       current
    DESCRIPTION
        "Cisco UCS vnic:LanConnTempl:intId managed object property"
    ::= { cucsVnicLanConnTemplEntry 6 }

cucsVnicLanConnTemplMtu OBJECT-TYPE
    SYNTAX       Gauge32
    MAX-ACCESS   read-only
    STATUS       current
    DESCRIPTION
        "Cisco UCS vnic:LanConnTempl:mtu managed object property"
    ::= { cucsVnicLanConnTemplEntry 7 }

cucsVnicLanConnTemplName OBJECT-TYPE
    SYNTAX       SnmpAdminString
    MAX-ACCESS   read-only
    STATUS       current
    DESCRIPTION
        "Cisco UCS vnic:LanConnTempl:name managed object property"
    ::= { cucsVnicLanConnTemplEntry 8 }

cucsVnicLanConnTemplNwCtrlPolicyName OBJECT-TYPE
    SYNTAX       SnmpAdminString
    MAX-ACCESS   read-only
    STATUS       current
    DESCRIPTION
        "Cisco UCS vnic:LanConnTempl:nwCtrlPolicyName managed
        object property"
    ::= { cucsVnicLanConnTemplEntry 9 }

cucsVnicLanConnTemplOperIdentPoolName OBJECT-TYPE
    SYNTAX       SnmpAdminString
    MAX-ACCESS   read-only
    STATUS       current
    DESCRIPTION
        "Cisco UCS vnic:LanConnTempl:operIdentPoolName
        managed object property"
    ::= { cucsVnicLanConnTemplEntry 10 }

cucsVnicLanConnTemplOperNwCtrlPolicyName OBJECT-TYPE
    SYNTAX       SnmpAdminString
    MAX-ACCESS   read-only
    STATUS       current
    DESCRIPTION
        "Cisco UCS vnic:LanConnTempl:operNwCtrlPolicyName
        managed object property"
    ::= { cucsVnicLanConnTemplEntry 11 }

cucsVnicLanConnTemplOperQosPolicyName OBJECT-TYPE
    SYNTAX       SnmpAdminString
    MAX-ACCESS   read-only
    STATUS       current
    DESCRIPTION
        "Cisco UCS vnic:LanConnTempl:operQosPolicyName
        managed object property"
    ::= { cucsVnicLanConnTemplEntry 12 }

cucsVnicLanConnTemplOperStatsPolicyName OBJECT-TYPE
    SYNTAX       SnmpAdminString
    MAX-ACCESS   read-only
    STATUS       current
    DESCRIPTION
        "Cisco UCS vnic:LanConnTempl:operStatsPolicyName
        managed object property"
    ::= { cucsVnicLanConnTemplEntry 13 }

cucsVnicLanConnTemplPinToGroupName OBJECT-TYPE
    SYNTAX       SnmpAdminString
    MAX-ACCESS   read-only
    STATUS       current
    DESCRIPTION
        "Cisco UCS vnic:LanConnTempl:pinToGroupName managed
        object property"
    ::= { cucsVnicLanConnTemplEntry 14 }

cucsVnicLanConnTemplQosPolicyName OBJECT-TYPE
    SYNTAX       SnmpAdminString
    MAX-ACCESS   read-only
    STATUS       current
    DESCRIPTION
        "Cisco UCS vnic:LanConnTempl:qosPolicyName managed
        object property"
    ::= { cucsVnicLanConnTemplEntry 15 }

cucsVnicLanConnTemplStatsPolicyName OBJECT-TYPE
    SYNTAX       SnmpAdminString
    MAX-ACCESS   read-only
    STATUS       current
    DESCRIPTION
        "Cisco UCS vnic:LanConnTempl:statsPolicyName managed
        object property"
    ::= { cucsVnicLanConnTemplEntry 16 }

cucsVnicLanConnTemplSwitchId OBJECT-TYPE
    SYNTAX       CucsVnicLanConnTemplSwitchId
    MAX-ACCESS   read-only
    STATUS       current
    DESCRIPTION
        "Cisco UCS vnic:LanConnTempl:switchId managed object property"
    ::= { cucsVnicLanConnTemplEntry 17 }

cucsVnicLanConnTemplTarget OBJECT-TYPE
    SYNTAX       CucsVnicTemplateTarget
    MAX-ACCESS   read-only
    STATUS       current
    DESCRIPTION
        "Cisco UCS vnic:LanConnTempl:target managed object property"
    ::= { cucsVnicLanConnTemplEntry 18 }

cucsVnicLanConnTemplTemplType OBJECT-TYPE
    SYNTAX       CucsVnicTemplateType
    MAX-ACCESS   read-only
    STATUS       current
    DESCRIPTION
        "Cisco UCS vnic:LanConnTempl:templType managed object property"
    ::= { cucsVnicLanConnTemplEntry 19 }

cucsVnicLifVlanTable OBJECT-TYPE
    SYNTAX           SEQUENCE OF CucsVnicLifVlanEntry
    MAX-ACCESS       not-accessible
    STATUS           current
    DESCRIPTION
        "Cisco UCS vnic:LifVlan managed object table"
    ::= { cucsVnicObjects 26 }

cucsVnicLifVlanEntry OBJECT-TYPE
    SYNTAX           CucsVnicLifVlanEntry
    MAX-ACCESS       not-accessible
    STATUS           current
    DESCRIPTION
        "Entry for the cucsVnicLifVlanTable table."
    INDEX { cucsVnicLifVlanInstanceId }
    ::= { cucsVnicLifVlanTable 1 }

CucsVnicLifVlanEntry ::= SEQUENCE {
    cucsVnicLifVlanInstanceId                                        CucsManagedObjectId,
    cucsVnicLifVlanDn                                                CucsManagedObjectDn,
    cucsVnicLifVlanRn                                                SnmpAdminString,
    cucsVnicLifVlanAddr                                              MacAddress,
    cucsVnicLifVlanDefaultNet                                        TruthValue,
    cucsVnicLifVlanName                                              SnmpAdminString,
    cucsVnicLifVlanOperState                                         CucsVnicIfOperState,
    cucsVnicLifVlanOwner                                             CucsVnicConnectionOwner,
    cucsVnicLifVlanSwitchId                                          CucsVnicL2IfSwitchId,
    cucsVnicLifVlanType                                              CucsVnicAEtherIfType,
    cucsVnicLifVlanVnet                                              Gauge32
}

cucsVnicLifVlanInstanceId OBJECT-TYPE
    SYNTAX       CucsManagedObjectId
    MAX-ACCESS   not-accessible
    STATUS       current
    DESCRIPTION
        "Instance identifier of the managed object."
    ::= { cucsVnicLifVlanEntry 1 }

cucsVnicLifVlanDn OBJECT-TYPE
    SYNTAX       CucsManagedObjectDn
    MAX-ACCESS   read-only
    STATUS       current
    DESCRIPTION
        "Cisco UCS vnic:LifVlan:dn managed object property"
    ::= { cucsVnicLifVlanEntry 2 }

cucsVnicLifVlanRn OBJECT-TYPE
    SYNTAX       SnmpAdminString
    MAX-ACCESS   read-only
    STATUS       current
    DESCRIPTION
        "Cisco UCS vnic:LifVlan:rn managed object property"
    ::= { cucsVnicLifVlanEntry 3 }

cucsVnicLifVlanAddr OBJECT-TYPE
    SYNTAX       MacAddress
    MAX-ACCESS   read-only
    STATUS       current
    DESCRIPTION
        "Cisco UCS vnic:LifVlan:addr managed object property"
    ::= { cucsVnicLifVlanEntry 4 }

cucsVnicLifVlanDefaultNet OBJECT-TYPE
    SYNTAX       TruthValue
    MAX-ACCESS   read-only
    STATUS       current
    DESCRIPTION
        "Cisco UCS vnic:LifVlan:defaultNet managed object property"
    ::= { cucsVnicLifVlanEntry 5 }

cucsVnicLifVlanName OBJECT-TYPE
    SYNTAX       SnmpAdminString
    MAX-ACCESS   read-only
    STATUS       current
    DESCRIPTION
        "Cisco UCS vnic:LifVlan:name managed object property"
    ::= { cucsVnicLifVlanEntry 6 }

cucsVnicLifVlanOperState OBJECT-TYPE
    SYNTAX       CucsVnicIfOperState
    MAX-ACCESS   read-only
    STATUS       current
    DESCRIPTION
        "Cisco UCS vnic:LifVlan:operState managed object property"
    ::= { cucsVnicLifVlanEntry 7 }

cucsVnicLifVlanOwner OBJECT-TYPE
    SYNTAX       CucsVnicConnectionOwner
    MAX-ACCESS   read-only
    STATUS       current
    DESCRIPTION
        "Cisco UCS vnic:LifVlan:owner managed object property"
    ::= { cucsVnicLifVlanEntry 8 }

cucsVnicLifVlanSwitchId OBJECT-TYPE
    SYNTAX       CucsVnicL2IfSwitchId
    MAX-ACCESS   read-only
    STATUS       current
    DESCRIPTION
        "Cisco UCS vnic:LifVlan:switchId managed object property"
    ::= { cucsVnicLifVlanEntry 9 }

cucsVnicLifVlanType OBJECT-TYPE
    SYNTAX       CucsVnicAEtherIfType
    MAX-ACCESS   read-only
    STATUS       current
    DESCRIPTION
        "Cisco UCS vnic:LifVlan:type managed object property"
    ::= { cucsVnicLifVlanEntry 10 }

cucsVnicLifVlanVnet OBJECT-TYPE
    SYNTAX       Gauge32
    MAX-ACCESS   read-only
    STATUS       current
    DESCRIPTION
        "Cisco UCS vnic:LifVlan:vnet managed object property"
    ::= { cucsVnicLifVlanEntry 11 }

cucsVnicLifVsanTable OBJECT-TYPE
    SYNTAX           SEQUENCE OF CucsVnicLifVsanEntry
    MAX-ACCESS       not-accessible
    STATUS           current
    DESCRIPTION
        "Cisco UCS vnic:LifVsan managed object table"
    ::= { cucsVnicObjects 27 }

cucsVnicLifVsanEntry OBJECT-TYPE
    SYNTAX           CucsVnicLifVsanEntry
    MAX-ACCESS       not-accessible
    STATUS           current
    DESCRIPTION
        "Entry for the cucsVnicLifVsanTable table."
    INDEX { cucsVnicLifVsanInstanceId }
    ::= { cucsVnicLifVsanTable 1 }

CucsVnicLifVsanEntry ::= SEQUENCE {
    cucsVnicLifVsanInstanceId                                        CucsManagedObjectId,
    cucsVnicLifVsanDn                                                CucsManagedObjectDn,
    cucsVnicLifVsanRn                                                SnmpAdminString,
    cucsVnicLifVsanInitiator                                         Unsigned64,
    cucsVnicLifVsanName                                              SnmpAdminString,
    cucsVnicLifVsanOperState                                         CucsVnicIfOperState,
    cucsVnicLifVsanOwner                                             CucsVnicConnectionOwner,
    cucsVnicLifVsanSwitchId                                          CucsVnicL2IfSwitchId,
    cucsVnicLifVsanType                                              CucsVnicAFcIfType,
    cucsVnicLifVsanVnet                                              Gauge32
}

cucsVnicLifVsanInstanceId OBJECT-TYPE
    SYNTAX       CucsManagedObjectId
    MAX-ACCESS   not-accessible
    STATUS       current
    DESCRIPTION
        "Instance identifier of the managed object."
    ::= { cucsVnicLifVsanEntry 1 }

cucsVnicLifVsanDn OBJECT-TYPE
    SYNTAX       CucsManagedObjectDn
    MAX-ACCESS   read-only
    STATUS       current
    DESCRIPTION
        "Cisco UCS vnic:LifVsan:dn managed object property"
    ::= { cucsVnicLifVsanEntry 2 }

cucsVnicLifVsanRn OBJECT-TYPE
    SYNTAX       SnmpAdminString
    MAX-ACCESS   read-only
    STATUS       current
    DESCRIPTION
        "Cisco UCS vnic:LifVsan:rn managed object property"
    ::= { cucsVnicLifVsanEntry 3 }

cucsVnicLifVsanInitiator OBJECT-TYPE
    SYNTAX       Unsigned64
    MAX-ACCESS   read-only
    STATUS       current
    DESCRIPTION
        "Cisco UCS vnic:LifVsan:initiator managed object property"
    ::= { cucsVnicLifVsanEntry 4 }

cucsVnicLifVsanName OBJECT-TYPE
    SYNTAX       SnmpAdminString
    MAX-ACCESS   read-only
    STATUS       current
    DESCRIPTION
        "Cisco UCS vnic:LifVsan:name managed object property"
    ::= { cucsVnicLifVsanEntry 5 }

cucsVnicLifVsanOperState OBJECT-TYPE
    SYNTAX       CucsVnicIfOperState
    MAX-ACCESS   read-only
    STATUS       current
    DESCRIPTION
        "Cisco UCS vnic:LifVsan:operState managed object property"
    ::= { cucsVnicLifVsanEntry 6 }

cucsVnicLifVsanOwner OBJECT-TYPE
    SYNTAX       CucsVnicConnectionOwner
    MAX-ACCESS   read-only
    STATUS       current
    DESCRIPTION
        "Cisco UCS vnic:LifVsan:owner managed object property"
    ::= { cucsVnicLifVsanEntry 7 }

cucsVnicLifVsanSwitchId OBJECT-TYPE
    SYNTAX       CucsVnicL2IfSwitchId
    MAX-ACCESS   read-only
    STATUS       current
    DESCRIPTION
        "Cisco UCS vnic:LifVsan:switchId managed object property"
    ::= { cucsVnicLifVsanEntry 8 }

cucsVnicLifVsanType OBJECT-TYPE
    SYNTAX       CucsVnicAFcIfType
    MAX-ACCESS   read-only
    STATUS       current
    DESCRIPTION
        "Cisco UCS vnic:LifVsan:type managed object property"
    ::= { cucsVnicLifVsanEntry 9 }

cucsVnicLifVsanVnet OBJECT-TYPE
    SYNTAX       Gauge32
    MAX-ACCESS   read-only
    STATUS       current
    DESCRIPTION
        "Cisco UCS vnic:LifVsan:vnet managed object property"
    ::= { cucsVnicLifVsanEntry 10 }

cucsVnicLunTable OBJECT-TYPE
    SYNTAX           SEQUENCE OF CucsVnicLunEntry
    MAX-ACCESS       not-accessible
    STATUS           current
    DESCRIPTION
        "Cisco UCS vnic:Lun managed object table"
    ::= { cucsVnicObjects 43 }

cucsVnicLunEntry OBJECT-TYPE
    SYNTAX           CucsVnicLunEntry
    MAX-ACCESS       not-accessible
    STATUS           current
    DESCRIPTION
        "Entry for the cucsVnicLunTable table."
    INDEX { cucsVnicLunInstanceId }
    ::= { cucsVnicLunTable 1 }

CucsVnicLunEntry ::= SEQUENCE {
    cucsVnicLunInstanceId                                            CucsManagedObjectId,
    cucsVnicLunDn                                                    CucsManagedObjectDn,
    cucsVnicLunRn                                                    SnmpAdminString,
    cucsVnicLunBootable                                              TruthValue,
    cucsVnicLunId                                                    Gauge32
}

cucsVnicLunInstanceId OBJECT-TYPE
    SYNTAX       CucsManagedObjectId
    MAX-ACCESS   not-accessible
    STATUS       current
    DESCRIPTION
        "Instance identifier of the managed object."
    ::= { cucsVnicLunEntry 1 }

cucsVnicLunDn OBJECT-TYPE
    SYNTAX       CucsManagedObjectDn
    MAX-ACCESS   read-only
    STATUS       current
    DESCRIPTION
        "Cisco UCS vnic:Lun:dn managed object property"
    ::= { cucsVnicLunEntry 2 }

cucsVnicLunRn OBJECT-TYPE
    SYNTAX       SnmpAdminString
    MAX-ACCESS   read-only
    STATUS       current
    DESCRIPTION
        "Cisco UCS vnic:Lun:rn managed object property"
    ::= { cucsVnicLunEntry 3 }

cucsVnicLunBootable OBJECT-TYPE
    SYNTAX       TruthValue
    MAX-ACCESS   read-only
    STATUS       current
    DESCRIPTION
        "Cisco UCS vnic:Lun:bootable managed object property"
    ::= { cucsVnicLunEntry 4 }

cucsVnicLunId OBJECT-TYPE
    SYNTAX       Gauge32
    MAX-ACCESS   read-only
    STATUS       current
    DESCRIPTION
        "Cisco UCS vnic:Lun:id managed object property"
    ::= { cucsVnicLunEntry 5 }

cucsVnicOProfileAliasTable OBJECT-TYPE
    SYNTAX           SEQUENCE OF CucsVnicOProfileAliasEntry
    MAX-ACCESS       not-accessible
    STATUS           current
    DESCRIPTION
        "Cisco UCS vnic:OProfileAlias managed object table"
    ::= { cucsVnicObjects 44 }

cucsVnicOProfileAliasEntry OBJECT-TYPE
    SYNTAX           CucsVnicOProfileAliasEntry
    MAX-ACCESS       not-accessible
    STATUS           current
    DESCRIPTION
        "Entry for the cucsVnicOProfileAliasTable table."
    INDEX { cucsVnicOProfileAliasInstanceId }
    ::= { cucsVnicOProfileAliasTable 1 }

CucsVnicOProfileAliasEntry ::= SEQUENCE {
    cucsVnicOProfileAliasInstanceId                                  CucsManagedObjectId,
    cucsVnicOProfileAliasDn                                          CucsManagedObjectDn,
    cucsVnicOProfileAliasRn                                          SnmpAdminString,
    cucsVnicOProfileAliasAlias                                       SnmpAdminString,
    cucsVnicOProfileAliasMgmtPlane                                   CucsVmMgmtPlane,
    cucsVnicOProfileAliasVSwitchId                                   SnmpAdminString,
    cucsVnicOProfileAliasVSwitchName                                 SnmpAdminString
}

cucsVnicOProfileAliasInstanceId OBJECT-TYPE
    SYNTAX       CucsManagedObjectId
    MAX-ACCESS   not-accessible
    STATUS       current
    DESCRIPTION
        "Instance identifier of the managed object."
    ::= { cucsVnicOProfileAliasEntry 1 }

cucsVnicOProfileAliasDn OBJECT-TYPE
    SYNTAX       CucsManagedObjectDn
    MAX-ACCESS   read-only
    STATUS       current
    DESCRIPTION
        "Cisco UCS vnic:OProfileAlias:dn managed object property"
    ::= { cucsVnicOProfileAliasEntry 2 }

cucsVnicOProfileAliasRn OBJECT-TYPE
    SYNTAX       SnmpAdminString
    MAX-ACCESS   read-only
    STATUS       current
    DESCRIPTION
        "Cisco UCS vnic:OProfileAlias:rn managed object property"
    ::= { cucsVnicOProfileAliasEntry 3 }

cucsVnicOProfileAliasAlias OBJECT-TYPE
    SYNTAX       SnmpAdminString
    MAX-ACCESS   read-only
    STATUS       current
    DESCRIPTION
        "Cisco UCS vnic:OProfileAlias:alias managed object property"
    ::= { cucsVnicOProfileAliasEntry 4 }

cucsVnicOProfileAliasMgmtPlane OBJECT-TYPE
    SYNTAX       CucsVmMgmtPlane
    MAX-ACCESS   read-only
    STATUS       current
    DESCRIPTION
        "Cisco UCS vnic:OProfileAlias:mgmtPlane managed object property"
    ::= { cucsVnicOProfileAliasEntry 5 }

cucsVnicOProfileAliasVSwitchId OBJECT-TYPE
    SYNTAX       SnmpAdminString
    MAX-ACCESS   read-only
    STATUS       current
    DESCRIPTION
        "Cisco UCS vnic:OProfileAlias:vSwitchId managed object property"
    ::= { cucsVnicOProfileAliasEntry 6 }

cucsVnicOProfileAliasVSwitchName OBJECT-TYPE
    SYNTAX       SnmpAdminString
    MAX-ACCESS   read-only
    STATUS       current
    DESCRIPTION
        "Cisco UCS vnic:OProfileAlias:vSwitchName managed object property"
    ::= { cucsVnicOProfileAliasEntry 7 }

cucsVnicProfileTable OBJECT-TYPE
    SYNTAX           SEQUENCE OF CucsVnicProfileEntry
    MAX-ACCESS       not-accessible
    STATUS           current
    DESCRIPTION
        "Cisco UCS vnic:Profile managed object table"
    ::= { cucsVnicObjects 28 }

cucsVnicProfileEntry OBJECT-TYPE
    SYNTAX           CucsVnicProfileEntry
    MAX-ACCESS       not-accessible
    STATUS           current
    DESCRIPTION
        "Entry for the cucsVnicProfileTable table."
    INDEX { cucsVnicProfileInstanceId }
    ::= { cucsVnicProfileTable 1 }

CucsVnicProfileEntry ::= SEQUENCE {
    cucsVnicProfileInstanceId                                        CucsManagedObjectId,
    cucsVnicProfileDn                                                CucsManagedObjectDn,
    cucsVnicProfileRn                                                SnmpAdminString,
    cucsVnicProfileCdp                                               CucsNwctrlAdminState,
    cucsVnicProfileCos                                               Gauge32,
    cucsVnicProfileDescr                                             SnmpAdminString,
    cucsVnicProfileForgeMac                                          CucsDpsecForgedTransmit,
    cucsVnicProfileIntId                                             SnmpAdminString,
    cucsVnicProfileMaxPorts                                          Gauge32,
    cucsVnicProfileName                                              SnmpAdminString,
    cucsVnicProfileNwCtrlPolicyName                                  SnmpAdminString,
    cucsVnicProfileOperNwCtrlPolicyName                              SnmpAdminString,
    cucsVnicProfileOperQosPolicyName                                 SnmpAdminString,
    cucsVnicProfilePinToGroupName                                    SnmpAdminString,
    cucsVnicProfileQosPolicyId                                       SnmpAdminString,
    cucsVnicProfileQosPolicyName                                     SnmpAdminString,
    cucsVnicProfileSwABorderPort                                     Gauge32,
    cucsVnicProfileSwABorderSlot                                     Gauge32,
    cucsVnicProfileSwBBorderPort                                     Gauge32,
    cucsVnicProfileSwBBorderSlot                                     Gauge32,
    cucsVnicProfileUplinkFailAction                                  CucsNwctrlLinkFailAction,
    cucsVnicProfileHostNwIOPerf                                      CucsVnicHostNwIOPerfPref,
    cucsVnicProfilePrimaryVlanId                                     Gauge32,
    cucsVnicProfileQosPolicyDn                                       SnmpAdminString
}

cucsVnicProfileInstanceId OBJECT-TYPE
    SYNTAX       CucsManagedObjectId
    MAX-ACCESS   not-accessible
    STATUS       current
    DESCRIPTION
        "Instance identifier of the managed object."
    ::= { cucsVnicProfileEntry 1 }

cucsVnicProfileDn OBJECT-TYPE
    SYNTAX       CucsManagedObjectDn
    MAX-ACCESS   read-only
    STATUS       current
    DESCRIPTION
        "Cisco UCS vnic:Profile:dn managed object property"
    ::= { cucsVnicProfileEntry 2 }

cucsVnicProfileRn OBJECT-TYPE
    SYNTAX       SnmpAdminString
    MAX-ACCESS   read-only
    STATUS       current
    DESCRIPTION
        "Cisco UCS vnic:Profile:rn managed object property"
    ::= { cucsVnicProfileEntry 3 }

cucsVnicProfileCdp OBJECT-TYPE
    SYNTAX       CucsNwctrlAdminState
    MAX-ACCESS   read-only
    STATUS       current
    DESCRIPTION
        "Cisco UCS vnic:Profile:cdp managed object property"
    ::= { cucsVnicProfileEntry 5 }

cucsVnicProfileCos OBJECT-TYPE
    SYNTAX       Gauge32
    MAX-ACCESS   read-only
    STATUS       current
    DESCRIPTION
        "Cisco UCS vnic:Profile:cos managed object property"
    ::= { cucsVnicProfileEntry 6 }

cucsVnicProfileDescr OBJECT-TYPE
    SYNTAX       SnmpAdminString
    MAX-ACCESS   read-only
    STATUS       current
    DESCRIPTION
        "Cisco UCS vnic:Profile:descr managed object property"
    ::= { cucsVnicProfileEntry 7 }

cucsVnicProfileForgeMac OBJECT-TYPE
    SYNTAX       CucsDpsecForgedTransmit
    MAX-ACCESS   read-only
    STATUS       current
    DESCRIPTION
        "Cisco UCS vnic:Profile:forgeMac managed object property"
    ::= { cucsVnicProfileEntry 8 }

cucsVnicProfileIntId OBJECT-TYPE
    SYNTAX       SnmpAdminString
    MAX-ACCESS   read-only
    STATUS       current
    DESCRIPTION
        "Cisco UCS vnic:Profile:intId managed object property"
    ::= { cucsVnicProfileEntry 9 }

cucsVnicProfileMaxPorts OBJECT-TYPE
    SYNTAX       Gauge32
    MAX-ACCESS   read-only
    STATUS       current
    DESCRIPTION
        "Cisco UCS vnic:Profile:maxPorts managed object property"
    ::= { cucsVnicProfileEntry 10 }

cucsVnicProfileName OBJECT-TYPE
    SYNTAX       SnmpAdminString
    MAX-ACCESS   read-only
    STATUS       current
    DESCRIPTION
        "Cisco UCS vnic:Profile:name managed object property"
    ::= { cucsVnicProfileEntry 11 }

cucsVnicProfileNwCtrlPolicyName OBJECT-TYPE
    SYNTAX       SnmpAdminString
    MAX-ACCESS   read-only
    STATUS       current
    DESCRIPTION
        "Cisco UCS vnic:Profile:nwCtrlPolicyName managed object property"
    ::= { cucsVnicProfileEntry 12 }

cucsVnicProfileOperNwCtrlPolicyName OBJECT-TYPE
    SYNTAX       SnmpAdminString
    MAX-ACCESS   read-only
    STATUS       current
    DESCRIPTION
        "Cisco UCS vnic:Profile:operNwCtrlPolicyName managed
        object property"
    ::= { cucsVnicProfileEntry 13 }

cucsVnicProfileOperQosPolicyName OBJECT-TYPE
    SYNTAX       SnmpAdminString
    MAX-ACCESS   read-only
    STATUS       current
    DESCRIPTION
        "Cisco UCS vnic:Profile:operQosPolicyName managed object property"
    ::= { cucsVnicProfileEntry 14 }

cucsVnicProfilePinToGroupName OBJECT-TYPE
    SYNTAX       SnmpAdminString
    MAX-ACCESS   read-only
    STATUS       current
    DESCRIPTION
        "Cisco UCS vnic:Profile:pinToGroupName managed object property"
    ::= { cucsVnicProfileEntry 15 }

cucsVnicProfileQosPolicyId OBJECT-TYPE
    SYNTAX       SnmpAdminString
    MAX-ACCESS   read-only
    STATUS       current
    DESCRIPTION
        "Cisco UCS vnic:Profile:qosPolicyId managed object property"
    ::= { cucsVnicProfileEntry 16 }

cucsVnicProfileQosPolicyName OBJECT-TYPE
    SYNTAX       SnmpAdminString
    MAX-ACCESS   read-only
    STATUS       current
    DESCRIPTION
        "Cisco UCS vnic:Profile:qosPolicyName managed object property"
    ::= { cucsVnicProfileEntry 17 }

cucsVnicProfileSwABorderPort OBJECT-TYPE
    SYNTAX       Gauge32
    MAX-ACCESS   read-only
    STATUS       current
    DESCRIPTION
        "Cisco UCS vnic:Profile:swABorderPort managed object property"
    ::= { cucsVnicProfileEntry 19 }

cucsVnicProfileSwABorderSlot OBJECT-TYPE
    SYNTAX       Gauge32
    MAX-ACCESS   read-only
    STATUS       current
    DESCRIPTION
        "Cisco UCS vnic:Profile:swABorderSlot managed object property"
    ::= { cucsVnicProfileEntry 20 }

cucsVnicProfileSwBBorderPort OBJECT-TYPE
    SYNTAX       Gauge32
    MAX-ACCESS   read-only
    STATUS       current
    DESCRIPTION
        "Cisco UCS vnic:Profile:swBBorderPort managed object property"
    ::= { cucsVnicProfileEntry 21 }

cucsVnicProfileSwBBorderSlot OBJECT-TYPE
    SYNTAX       Gauge32
    MAX-ACCESS   read-only
    STATUS       current
    DESCRIPTION
        "Cisco UCS vnic:Profile:swBBorderSlot managed object property"
    ::= { cucsVnicProfileEntry 22 }

cucsVnicProfileUplinkFailAction OBJECT-TYPE
    SYNTAX       CucsNwctrlLinkFailAction
    MAX-ACCESS   read-only
    STATUS       current
    DESCRIPTION
        "Cisco UCS vnic:Profile:uplinkFailAction managed object property"
    ::= { cucsVnicProfileEntry 23 }

cucsVnicProfileHostNwIOPerf OBJECT-TYPE
    SYNTAX       CucsVnicHostNwIOPerfPref
    MAX-ACCESS   read-only
    STATUS       current
    DESCRIPTION
        "Cisco UCS vnic:Profile:hostNwIOPerf managed object property"
    ::= { cucsVnicProfileEntry 24 }

cucsVnicProfilePrimaryVlanId OBJECT-TYPE
    SYNTAX       Gauge32
    MAX-ACCESS   read-only
    STATUS       current
    DESCRIPTION
        "Cisco UCS vnic:Profile:primaryVlanId managed object property"
    ::= { cucsVnicProfileEntry 25 }

cucsVnicProfileQosPolicyDn OBJECT-TYPE
    SYNTAX       SnmpAdminString
    MAX-ACCESS   read-only
    STATUS       current
    DESCRIPTION
        "Cisco UCS vnic:Profile:qosPolicyDn managed object property"
    ::= { cucsVnicProfileEntry 26 }

cucsVnicProfileAliasTable OBJECT-TYPE
    SYNTAX           SEQUENCE OF CucsVnicProfileAliasEntry
    MAX-ACCESS       not-accessible
    STATUS           current
    DESCRIPTION
        "Cisco UCS vnic:ProfileAlias managed object table"
    ::= { cucsVnicObjects 29 }

cucsVnicProfileAliasEntry OBJECT-TYPE
    SYNTAX           CucsVnicProfileAliasEntry
    MAX-ACCESS       not-accessible
    STATUS           current
    DESCRIPTION
        "Entry for the cucsVnicProfileAliasTable table."
    INDEX { cucsVnicProfileAliasInstanceId }
    ::= { cucsVnicProfileAliasTable 1 }

CucsVnicProfileAliasEntry ::= SEQUENCE {
    cucsVnicProfileAliasInstanceId                                   CucsManagedObjectId,
    cucsVnicProfileAliasDn                                           CucsManagedObjectDn,
    cucsVnicProfileAliasRn                                           SnmpAdminString,
    cucsVnicProfileAliasAlias                                        SnmpAdminString,
    cucsVnicProfileAliasSwUuid                                       SnmpAdminString
}

cucsVnicProfileAliasInstanceId OBJECT-TYPE
    SYNTAX       CucsManagedObjectId
    MAX-ACCESS   not-accessible
    STATUS       current
    DESCRIPTION
        "Instance identifier of the managed object."
    ::= { cucsVnicProfileAliasEntry 1 }

cucsVnicProfileAliasDn OBJECT-TYPE
    SYNTAX       CucsManagedObjectDn
    MAX-ACCESS   read-only
    STATUS       current
    DESCRIPTION
        "Cisco UCS vnic:ProfileAlias:dn managed object property"
    ::= { cucsVnicProfileAliasEntry 2 }

cucsVnicProfileAliasRn OBJECT-TYPE
    SYNTAX       SnmpAdminString
    MAX-ACCESS   read-only
    STATUS       current
    DESCRIPTION
        "Cisco UCS vnic:ProfileAlias:rn managed object property"
    ::= { cucsVnicProfileAliasEntry 3 }

cucsVnicProfileAliasAlias OBJECT-TYPE
    SYNTAX       SnmpAdminString
    MAX-ACCESS   read-only
    STATUS       current
    DESCRIPTION
        "Cisco UCS vnic:ProfileAlias:alias managed object property"
    ::= { cucsVnicProfileAliasEntry 4 }

cucsVnicProfileAliasSwUuid OBJECT-TYPE
    SYNTAX       SnmpAdminString
    MAX-ACCESS   read-only
    STATUS       current
    DESCRIPTION
        "Cisco UCS vnic:ProfileAlias:swUuid managed object property"
    ::= { cucsVnicProfileAliasEntry 5 }

cucsVnicProfileSetTable OBJECT-TYPE
    SYNTAX           SEQUENCE OF CucsVnicProfileSetEntry
    MAX-ACCESS       not-accessible
    STATUS           current
    DESCRIPTION
        "Cisco UCS vnic:ProfileSet managed object table"
    ::= { cucsVnicObjects 30 }

cucsVnicProfileSetEntry OBJECT-TYPE
    SYNTAX           CucsVnicProfileSetEntry
    MAX-ACCESS       not-accessible
    STATUS           current
    DESCRIPTION
        "Entry for the cucsVnicProfileSetTable table."
    INDEX { cucsVnicProfileSetInstanceId }
    ::= { cucsVnicProfileSetTable 1 }

CucsVnicProfileSetEntry ::= SEQUENCE {
    cucsVnicProfileSetInstanceId                                     CucsManagedObjectId,
    cucsVnicProfileSetDn                                             CucsManagedObjectDn,
    cucsVnicProfileSetRn                                             SnmpAdminString,
    cucsVnicProfileSetFsmDescr                                       SnmpAdminString,
    cucsVnicProfileSetFsmPrev                                        SnmpAdminString,
    cucsVnicProfileSetFsmProgr                                       Gauge32,
    cucsVnicProfileSetFsmRmtInvErrCode                               Gauge32,
    cucsVnicProfileSetFsmRmtInvErrDescr                              SnmpAdminString,
    cucsVnicProfileSetFsmRmtInvRslt                                  CucsConditionRemoteInvRslt,
    cucsVnicProfileSetFsmStageDescr                                  SnmpAdminString,
    cucsVnicProfileSetFsmStamp                                       DateAndTime,
    cucsVnicProfileSetFsmStatus                                      SnmpAdminString,
    cucsVnicProfileSetFsmTry                                         Gauge32
}

cucsVnicProfileSetInstanceId OBJECT-TYPE
    SYNTAX       CucsManagedObjectId
    MAX-ACCESS   not-accessible
    STATUS       current
    DESCRIPTION
        "Instance identifier of the managed object."
    ::= { cucsVnicProfileSetEntry 1 }

cucsVnicProfileSetDn OBJECT-TYPE
    SYNTAX       CucsManagedObjectDn
    MAX-ACCESS   read-only
    STATUS       current
    DESCRIPTION
        "Cisco UCS vnic:ProfileSet:dn managed object property"
    ::= { cucsVnicProfileSetEntry 2 }

cucsVnicProfileSetRn OBJECT-TYPE
    SYNTAX       SnmpAdminString
    MAX-ACCESS   read-only
    STATUS       current
    DESCRIPTION
        "Cisco UCS vnic:ProfileSet:rn managed object property"
    ::= { cucsVnicProfileSetEntry 3 }

cucsVnicProfileSetFsmDescr OBJECT-TYPE
    SYNTAX       SnmpAdminString
    MAX-ACCESS   read-only
    STATUS       current
    DESCRIPTION
        "Cisco UCS vnic:ProfileSet:fsmDescr managed object property"
    ::= { cucsVnicProfileSetEntry 4 }

cucsVnicProfileSetFsmPrev OBJECT-TYPE
    SYNTAX       SnmpAdminString
    MAX-ACCESS   read-only
    STATUS       current
    DESCRIPTION
        "Cisco UCS vnic:ProfileSet:fsmPrev managed object property"
    ::= { cucsVnicProfileSetEntry 5 }

cucsVnicProfileSetFsmProgr OBJECT-TYPE
    SYNTAX       Gauge32
    MAX-ACCESS   read-only
    STATUS       current
    DESCRIPTION
        "Cisco UCS vnic:ProfileSet:fsmProgr managed object property"
    ::= { cucsVnicProfileSetEntry 6 }

cucsVnicProfileSetFsmRmtInvErrCode OBJECT-TYPE
    SYNTAX       Gauge32
    MAX-ACCESS   read-only
    STATUS       current
    DESCRIPTION
        "Cisco UCS vnic:ProfileSet:fsmRmtInvErrCode managed
        object property"
    ::= { cucsVnicProfileSetEntry 7 }

cucsVnicProfileSetFsmRmtInvErrDescr OBJECT-TYPE
    SYNTAX       SnmpAdminString
    MAX-ACCESS   read-only
    STATUS       current
    DESCRIPTION
        "Cisco UCS vnic:ProfileSet:fsmRmtInvErrDescr managed
        object property"
    ::= { cucsVnicProfileSetEntry 8 }

cucsVnicProfileSetFsmRmtInvRslt OBJECT-TYPE
    SYNTAX       CucsConditionRemoteInvRslt
    MAX-ACCESS   read-only
    STATUS       current
    DESCRIPTION
        "Cisco UCS vnic:ProfileSet:fsmRmtInvRslt managed object property"
    ::= { cucsVnicProfileSetEntry 9 }

cucsVnicProfileSetFsmStageDescr OBJECT-TYPE
    SYNTAX       SnmpAdminString
    MAX-ACCESS   read-only
    STATUS       current
    DESCRIPTION
        "Cisco UCS vnic:ProfileSet:fsmStageDescr managed object property"
    ::= { cucsVnicProfileSetEntry 10 }

cucsVnicProfileSetFsmStamp OBJECT-TYPE
    SYNTAX       DateAndTime
    MAX-ACCESS   read-only
    STATUS       current
    DESCRIPTION
        "Cisco UCS vnic:ProfileSet:fsmStamp managed object property"
    ::= { cucsVnicProfileSetEntry 11 }

cucsVnicProfileSetFsmStatus OBJECT-TYPE
    SYNTAX       SnmpAdminString
    MAX-ACCESS   read-only
    STATUS       current
    DESCRIPTION
        "Cisco UCS vnic:ProfileSet:fsmStatus managed object property"
    ::= { cucsVnicProfileSetEntry 12 }

cucsVnicProfileSetFsmTry OBJECT-TYPE
    SYNTAX       Gauge32
    MAX-ACCESS   read-only
    STATUS       current
    DESCRIPTION
        "Cisco UCS vnic:ProfileSet:fsmTry managed object property"
    ::= { cucsVnicProfileSetEntry 13 }

cucsVnicProfileSetFsmTaskTable OBJECT-TYPE
    SYNTAX           SEQUENCE OF CucsVnicProfileSetFsmTaskEntry
    MAX-ACCESS       not-accessible
    STATUS           current
    DESCRIPTION
        "Cisco UCS vnic:ProfileSetFsmTask managed object table"
    ::= { cucsVnicObjects 31 }

cucsVnicProfileSetFsmTaskEntry OBJECT-TYPE
    SYNTAX           CucsVnicProfileSetFsmTaskEntry
    MAX-ACCESS       not-accessible
    STATUS           current
    DESCRIPTION
        "Entry for the cucsVnicProfileSetFsmTaskTable table."
    INDEX { cucsVnicProfileSetFsmTaskInstanceId }
    ::= { cucsVnicProfileSetFsmTaskTable 1 }

CucsVnicProfileSetFsmTaskEntry ::= SEQUENCE {
    cucsVnicProfileSetFsmTaskInstanceId                              CucsManagedObjectId,
    cucsVnicProfileSetFsmTaskDn                                      CucsManagedObjectDn,
    cucsVnicProfileSetFsmTaskRn                                      SnmpAdminString,
    cucsVnicProfileSetFsmTaskCompletion                              CucsFsmCompletion,
    cucsVnicProfileSetFsmTaskFlags                                   CucsFsmFlags,
    cucsVnicProfileSetFsmTaskItem                                    CucsVnicProfileSetFsmTaskItem,
    cucsVnicProfileSetFsmTaskSeqId                                   Gauge32
}

cucsVnicProfileSetFsmTaskInstanceId OBJECT-TYPE
    SYNTAX       CucsManagedObjectId
    MAX-ACCESS   not-accessible
    STATUS       current
    DESCRIPTION
        "Instance identifier of the managed object."
    ::= { cucsVnicProfileSetFsmTaskEntry 1 }

cucsVnicProfileSetFsmTaskDn OBJECT-TYPE
    SYNTAX       CucsManagedObjectDn
    MAX-ACCESS   read-only
    STATUS       current
    DESCRIPTION
        "Cisco UCS vnic:ProfileSetFsmTask:dn managed object property"
    ::= { cucsVnicProfileSetFsmTaskEntry 2 }

cucsVnicProfileSetFsmTaskRn OBJECT-TYPE
    SYNTAX       SnmpAdminString
    MAX-ACCESS   read-only
    STATUS       current
    DESCRIPTION
        "Cisco UCS vnic:ProfileSetFsmTask:rn managed object property"
    ::= { cucsVnicProfileSetFsmTaskEntry 3 }

cucsVnicProfileSetFsmTaskCompletion OBJECT-TYPE
    SYNTAX       CucsFsmCompletion
    MAX-ACCESS   read-only
    STATUS       current
    DESCRIPTION
        "Cisco UCS vnic:ProfileSetFsmTask:completion managed
        object property"
    ::= { cucsVnicProfileSetFsmTaskEntry 4 }

cucsVnicProfileSetFsmTaskFlags OBJECT-TYPE
    SYNTAX       CucsFsmFlags
    MAX-ACCESS   read-only
    STATUS       current
    DESCRIPTION
        "Cisco UCS vnic:ProfileSetFsmTask:flags managed object property"
    ::= { cucsVnicProfileSetFsmTaskEntry 5 }

cucsVnicProfileSetFsmTaskItem OBJECT-TYPE
    SYNTAX       CucsVnicProfileSetFsmTaskItem
    MAX-ACCESS   read-only
    STATUS       current
    DESCRIPTION
        "Cisco UCS vnic:ProfileSetFsmTask:item managed object property"
    ::= { cucsVnicProfileSetFsmTaskEntry 6 }

cucsVnicProfileSetFsmTaskSeqId OBJECT-TYPE
    SYNTAX       Gauge32
    MAX-ACCESS   read-only
    STATUS       current
    DESCRIPTION
        "Cisco UCS vnic:ProfileSetFsmTask:seqId managed object property"
    ::= { cucsVnicProfileSetFsmTaskEntry 7 }

cucsVnicSanConnTemplTable OBJECT-TYPE
    SYNTAX           SEQUENCE OF CucsVnicSanConnTemplEntry
    MAX-ACCESS       not-accessible
    STATUS           current
    DESCRIPTION
        "Cisco UCS vnic:SanConnTempl managed object table"
    ::= { cucsVnicObjects 32 }

cucsVnicSanConnTemplEntry OBJECT-TYPE
    SYNTAX           CucsVnicSanConnTemplEntry
    MAX-ACCESS       not-accessible
    STATUS           current
    DESCRIPTION
        "Entry for the cucsVnicSanConnTemplTable table."
    INDEX { cucsVnicSanConnTemplInstanceId }
    ::= { cucsVnicSanConnTemplTable 1 }

CucsVnicSanConnTemplEntry ::= SEQUENCE {
    cucsVnicSanConnTemplInstanceId                                   CucsManagedObjectId,
    cucsVnicSanConnTemplDn                                           CucsManagedObjectDn,
    cucsVnicSanConnTemplRn                                           SnmpAdminString,
    cucsVnicSanConnTemplDescr                                        SnmpAdminString,
    cucsVnicSanConnTemplIdentPoolName                                SnmpAdminString,
    cucsVnicSanConnTemplIntId                                        SnmpAdminString,
    cucsVnicSanConnTemplMaxDataFieldSize                             Gauge32,
    cucsVnicSanConnTemplName                                         SnmpAdminString,
    cucsVnicSanConnTemplNwCtrlPolicyName                             SnmpAdminString,
    cucsVnicSanConnTemplOperIdentPoolName                            SnmpAdminString,
    cucsVnicSanConnTemplOperQosPolicyName                            SnmpAdminString,
    cucsVnicSanConnTemplOperStatsPolicyName                          SnmpAdminString,
    cucsVnicSanConnTemplPinToGroupName                               SnmpAdminString,
    cucsVnicSanConnTemplQosPolicyName                                SnmpAdminString,
    cucsVnicSanConnTemplStatsPolicyName                              SnmpAdminString,
    cucsVnicSanConnTemplSwitchId                                     CucsNetworkSwitchId,
    cucsVnicSanConnTemplTarget                                       CucsVnicSanConnTemplTarget,
    cucsVnicSanConnTemplTemplType                                    CucsVnicTemplateType
}

cucsVnicSanConnTemplInstanceId OBJECT-TYPE
    SYNTAX       CucsManagedObjectId
    MAX-ACCESS   not-accessible
    STATUS       current
    DESCRIPTION
        "Instance identifier of the managed object."
    ::= { cucsVnicSanConnTemplEntry 1 }

cucsVnicSanConnTemplDn OBJECT-TYPE
    SYNTAX       CucsManagedObjectDn
    MAX-ACCESS   read-only
    STATUS       current
    DESCRIPTION
        "Cisco UCS vnic:SanConnTempl:dn managed object property"
    ::= { cucsVnicSanConnTemplEntry 2 }

cucsVnicSanConnTemplRn OBJECT-TYPE
    SYNTAX       SnmpAdminString
    MAX-ACCESS   read-only
    STATUS       current
    DESCRIPTION
        "Cisco UCS vnic:SanConnTempl:rn managed object property"
    ::= { cucsVnicSanConnTemplEntry 3 }

cucsVnicSanConnTemplDescr OBJECT-TYPE
    SYNTAX       SnmpAdminString
    MAX-ACCESS   read-only
    STATUS       current
    DESCRIPTION
        "Cisco UCS vnic:SanConnTempl:descr managed object property"
    ::= { cucsVnicSanConnTemplEntry 4 }

cucsVnicSanConnTemplIdentPoolName OBJECT-TYPE
    SYNTAX       SnmpAdminString
    MAX-ACCESS   read-only
    STATUS       current
    DESCRIPTION
        "Cisco UCS vnic:SanConnTempl:identPoolName managed
        object property"
    ::= { cucsVnicSanConnTemplEntry 5 }

cucsVnicSanConnTemplIntId OBJECT-TYPE
    SYNTAX       SnmpAdminString
    MAX-ACCESS   read-only
    STATUS       current
    DESCRIPTION
        "Cisco UCS vnic:SanConnTempl:intId managed object property"
    ::= { cucsVnicSanConnTemplEntry 6 }

cucsVnicSanConnTemplMaxDataFieldSize OBJECT-TYPE
    SYNTAX       Gauge32
    MAX-ACCESS   read-only
    STATUS       current
    DESCRIPTION
        "Cisco UCS vnic:SanConnTempl:maxDataFieldSize managed
        object property"
    ::= { cucsVnicSanConnTemplEntry 7 }

cucsVnicSanConnTemplName OBJECT-TYPE
    SYNTAX       SnmpAdminString
    MAX-ACCESS   read-only
    STATUS       current
    DESCRIPTION
        "Cisco UCS vnic:SanConnTempl:name managed object property"
    ::= { cucsVnicSanConnTemplEntry 8 }

cucsVnicSanConnTemplNwCtrlPolicyName OBJECT-TYPE
    SYNTAX       SnmpAdminString
    MAX-ACCESS   read-only
    STATUS       current
    DESCRIPTION
        "Cisco UCS vnic:SanConnTempl:nwCtrlPolicyName managed
        object property"
    ::= { cucsVnicSanConnTemplEntry 9 }

cucsVnicSanConnTemplOperIdentPoolName OBJECT-TYPE
    SYNTAX       SnmpAdminString
    MAX-ACCESS   read-only
    STATUS       current
    DESCRIPTION
        "Cisco UCS vnic:SanConnTempl:operIdentPoolName
        managed object property"
    ::= { cucsVnicSanConnTemplEntry 10 }

cucsVnicSanConnTemplOperQosPolicyName OBJECT-TYPE
    SYNTAX       SnmpAdminString
    MAX-ACCESS   read-only
    STATUS       current
    DESCRIPTION
        "Cisco UCS vnic:SanConnTempl:operQosPolicyName
        managed object property"
    ::= { cucsVnicSanConnTemplEntry 11 }

cucsVnicSanConnTemplOperStatsPolicyName OBJECT-TYPE
    SYNTAX       SnmpAdminString
    MAX-ACCESS   read-only
    STATUS       current
    DESCRIPTION
        "Cisco UCS vnic:SanConnTempl:operStatsPolicyName
        managed object property"
    ::= { cucsVnicSanConnTemplEntry 12 }

cucsVnicSanConnTemplPinToGroupName OBJECT-TYPE
    SYNTAX       SnmpAdminString
    MAX-ACCESS   read-only
    STATUS       current
    DESCRIPTION
        "Cisco UCS vnic:SanConnTempl:pinToGroupName managed
        object property"
    ::= { cucsVnicSanConnTemplEntry 13 }

cucsVnicSanConnTemplQosPolicyName OBJECT-TYPE
    SYNTAX       SnmpAdminString
    MAX-ACCESS   read-only
    STATUS       current
    DESCRIPTION
        "Cisco UCS vnic:SanConnTempl:qosPolicyName managed
        object property"
    ::= { cucsVnicSanConnTemplEntry 14 }

cucsVnicSanConnTemplStatsPolicyName OBJECT-TYPE
    SYNTAX       SnmpAdminString
    MAX-ACCESS   read-only
    STATUS       current
    DESCRIPTION
        "Cisco UCS vnic:SanConnTempl:statsPolicyName managed
        object property"
    ::= { cucsVnicSanConnTemplEntry 15 }

cucsVnicSanConnTemplSwitchId OBJECT-TYPE
    SYNTAX       CucsNetworkSwitchId
    MAX-ACCESS   read-only
    STATUS       current
    DESCRIPTION
        "Cisco UCS vnic:SanConnTempl:switchId managed object property"
    ::= { cucsVnicSanConnTemplEntry 16 }

cucsVnicSanConnTemplTarget OBJECT-TYPE
    SYNTAX       CucsVnicSanConnTemplTarget
    MAX-ACCESS   read-only
    STATUS       current
    DESCRIPTION
        "Cisco UCS vnic:SanConnTempl:target managed object property"
    ::= { cucsVnicSanConnTemplEntry 17 }

cucsVnicSanConnTemplTemplType OBJECT-TYPE
    SYNTAX       CucsVnicTemplateType
    MAX-ACCESS   read-only
    STATUS       current
    DESCRIPTION
        "Cisco UCS vnic:SanConnTempl:templType managed object property"
    ::= { cucsVnicSanConnTemplEntry 18 }

cucsVnicScsiTable OBJECT-TYPE
    SYNTAX           SEQUENCE OF CucsVnicScsiEntry
    MAX-ACCESS       not-accessible
    STATUS           current
    DESCRIPTION
        "Cisco UCS vnic:Scsi managed object table"
    ::= { cucsVnicObjects 33 }

cucsVnicScsiEntry OBJECT-TYPE
    SYNTAX           CucsVnicScsiEntry
    MAX-ACCESS       not-accessible
    STATUS           current
    DESCRIPTION
        "Entry for the cucsVnicScsiTable table."
    INDEX { cucsVnicScsiInstanceId }
    ::= { cucsVnicScsiTable 1 }

CucsVnicScsiEntry ::= SEQUENCE {
    cucsVnicScsiInstanceId                                           CucsManagedObjectId,
    cucsVnicScsiDn                                                   CucsManagedObjectDn,
    cucsVnicScsiRn                                                   SnmpAdminString,
    cucsVnicScsiAdaptorProfileName                                   SnmpAdminString,
    cucsVnicScsiAdminVcon                                            SnmpAdminString,
    cucsVnicScsiBootDev                                              CucsVnicVnicBootDev,
    cucsVnicScsiConfigState                                          CucsLsConfigState,
    cucsVnicScsiEquipmentDn                                          SnmpAdminString,
    cucsVnicScsiIdentPoolName                                        SnmpAdminString,
    cucsVnicScsiInstType                                             CucsVnicInstantiation,
    cucsVnicScsiName                                                 SnmpAdminString,
    cucsVnicScsiNwTemplName                                          SnmpAdminString,
    cucsVnicScsiOperOrder                                            Gauge32,
    cucsVnicScsiOperSpeed                                            Gauge32,
    cucsVnicScsiOperStatsPolicyName                                  SnmpAdminString,
    cucsVnicScsiOperVcon                                             SnmpAdminString,
    cucsVnicScsiOrder                                                Gauge32,
    cucsVnicScsiOwner                                                CucsVnicConnectionOwner,
    cucsVnicScsiPinToGroupName                                       SnmpAdminString,
    cucsVnicScsiQosPolicyName                                        SnmpAdminString,
    cucsVnicScsiStatsPolicyName                                      SnmpAdminString,
    cucsVnicScsiSwitchId                                             CucsNetworkSwitchId,
    cucsVnicScsiType                                                 CucsVnicScsiType
}

cucsVnicScsiInstanceId OBJECT-TYPE
    SYNTAX       CucsManagedObjectId
    MAX-ACCESS   not-accessible
    STATUS       current
    DESCRIPTION
        "Instance identifier of the managed object."
    ::= { cucsVnicScsiEntry 1 }

cucsVnicScsiDn OBJECT-TYPE
    SYNTAX       CucsManagedObjectDn
    MAX-ACCESS   read-only
    STATUS       current
    DESCRIPTION
        "Cisco UCS vnic:Scsi:dn managed object property"
    ::= { cucsVnicScsiEntry 2 }

cucsVnicScsiRn OBJECT-TYPE
    SYNTAX       SnmpAdminString
    MAX-ACCESS   read-only
    STATUS       current
    DESCRIPTION
        "Cisco UCS vnic:Scsi:rn managed object property"
    ::= { cucsVnicScsiEntry 3 }

cucsVnicScsiAdaptorProfileName OBJECT-TYPE
    SYNTAX       SnmpAdminString
    MAX-ACCESS   read-only
    STATUS       current
    DESCRIPTION
        "Cisco UCS vnic:Scsi:adaptorProfileName managed object property"
    ::= { cucsVnicScsiEntry 4 }

cucsVnicScsiAdminVcon OBJECT-TYPE
    SYNTAX       SnmpAdminString
    MAX-ACCESS   read-only
    STATUS       current
    DESCRIPTION
        "Cisco UCS vnic:Scsi:adminVcon managed object property"
    ::= { cucsVnicScsiEntry 5 }

cucsVnicScsiBootDev OBJECT-TYPE
    SYNTAX       CucsVnicVnicBootDev
    MAX-ACCESS   read-only
    STATUS       current
    DESCRIPTION
        "Cisco UCS vnic:Scsi:bootDev managed object property"
    ::= { cucsVnicScsiEntry 6 }

cucsVnicScsiConfigState OBJECT-TYPE
    SYNTAX       CucsLsConfigState
    MAX-ACCESS   read-only
    STATUS       current
    DESCRIPTION
        "Cisco UCS vnic:Scsi:configState managed object property"
    ::= { cucsVnicScsiEntry 7 }

cucsVnicScsiEquipmentDn OBJECT-TYPE
    SYNTAX       SnmpAdminString
    MAX-ACCESS   read-only
    STATUS       current
    DESCRIPTION
        "Cisco UCS vnic:Scsi:equipmentDn managed object property"
    ::= { cucsVnicScsiEntry 8 }

cucsVnicScsiIdentPoolName OBJECT-TYPE
    SYNTAX       SnmpAdminString
    MAX-ACCESS   read-only
    STATUS       current
    DESCRIPTION
        "Cisco UCS vnic:Scsi:identPoolName managed object property"
    ::= { cucsVnicScsiEntry 9 }

cucsVnicScsiInstType OBJECT-TYPE
    SYNTAX       CucsVnicInstantiation
    MAX-ACCESS   read-only
    STATUS       current
    DESCRIPTION
        "Cisco UCS vnic:Scsi:instType managed object property"
    ::= { cucsVnicScsiEntry 10 }

cucsVnicScsiName OBJECT-TYPE
    SYNTAX       SnmpAdminString
    MAX-ACCESS   read-only
    STATUS       current
    DESCRIPTION
        "Cisco UCS vnic:Scsi:name managed object property"
    ::= { cucsVnicScsiEntry 11 }

cucsVnicScsiNwTemplName OBJECT-TYPE
    SYNTAX       SnmpAdminString
    MAX-ACCESS   read-only
    STATUS       current
    DESCRIPTION
        "Cisco UCS vnic:Scsi:nwTemplName managed object property"
    ::= { cucsVnicScsiEntry 12 }

cucsVnicScsiOperOrder OBJECT-TYPE
    SYNTAX       Gauge32
    MAX-ACCESS   read-only
    STATUS       current
    DESCRIPTION
        "Cisco UCS vnic:Scsi:operOrder managed object property"
    ::= { cucsVnicScsiEntry 13 }

cucsVnicScsiOperSpeed OBJECT-TYPE
    SYNTAX       Gauge32
    MAX-ACCESS   read-only
    STATUS       current
    DESCRIPTION
        "Cisco UCS vnic:Scsi:operSpeed managed object property"
    ::= { cucsVnicScsiEntry 14 }

cucsVnicScsiOperStatsPolicyName OBJECT-TYPE
    SYNTAX       SnmpAdminString
    MAX-ACCESS   read-only
    STATUS       current
    DESCRIPTION
        "Cisco UCS vnic:Scsi:operStatsPolicyName managed object property"
    ::= { cucsVnicScsiEntry 15 }

cucsVnicScsiOperVcon OBJECT-TYPE
    SYNTAX       SnmpAdminString
    MAX-ACCESS   read-only
    STATUS       current
    DESCRIPTION
        "Cisco UCS vnic:Scsi:operVcon managed object property"
    ::= { cucsVnicScsiEntry 16 }

cucsVnicScsiOrder OBJECT-TYPE
    SYNTAX       Gauge32
    MAX-ACCESS   read-only
    STATUS       current
    DESCRIPTION
        "Cisco UCS vnic:Scsi:order managed object property"
    ::= { cucsVnicScsiEntry 17 }

cucsVnicScsiOwner OBJECT-TYPE
    SYNTAX       CucsVnicConnectionOwner
    MAX-ACCESS   read-only
    STATUS       current
    DESCRIPTION
        "Cisco UCS vnic:Scsi:owner managed object property"
    ::= { cucsVnicScsiEntry 18 }

cucsVnicScsiPinToGroupName OBJECT-TYPE
    SYNTAX       SnmpAdminString
    MAX-ACCESS   read-only
    STATUS       current
    DESCRIPTION
        "Cisco UCS vnic:Scsi:pinToGroupName managed object property"
    ::= { cucsVnicScsiEntry 19 }

cucsVnicScsiQosPolicyName OBJECT-TYPE
    SYNTAX       SnmpAdminString
    MAX-ACCESS   read-only
    STATUS       current
    DESCRIPTION
        "Cisco UCS vnic:Scsi:qosPolicyName managed object property"
    ::= { cucsVnicScsiEntry 20 }

cucsVnicScsiStatsPolicyName OBJECT-TYPE
    SYNTAX       SnmpAdminString
    MAX-ACCESS   read-only
    STATUS       current
    DESCRIPTION
        "Cisco UCS vnic:Scsi:statsPolicyName managed object property"
    ::= { cucsVnicScsiEntry 21 }

cucsVnicScsiSwitchId OBJECT-TYPE
    SYNTAX       CucsNetworkSwitchId
    MAX-ACCESS   read-only
    STATUS       current
    DESCRIPTION
        "Cisco UCS vnic:Scsi:switchId managed object property"
    ::= { cucsVnicScsiEntry 22 }

cucsVnicScsiType OBJECT-TYPE
    SYNTAX       CucsVnicScsiType
    MAX-ACCESS   read-only
    STATUS       current
    DESCRIPTION
        "Cisco UCS vnic:Scsi:type managed object property"
    ::= { cucsVnicScsiEntry 23 }

cucsVnicScsiIfTable OBJECT-TYPE
    SYNTAX           SEQUENCE OF CucsVnicScsiIfEntry
    MAX-ACCESS       not-accessible
    STATUS           current
    DESCRIPTION
        "Cisco UCS vnic:ScsiIf managed object table"
    ::= { cucsVnicObjects 34 }

cucsVnicScsiIfEntry OBJECT-TYPE
    SYNTAX           CucsVnicScsiIfEntry
    MAX-ACCESS       not-accessible
    STATUS           current
    DESCRIPTION
        "Entry for the cucsVnicScsiIfTable table."
    INDEX { cucsVnicScsiIfInstanceId }
    ::= { cucsVnicScsiIfTable 1 }

CucsVnicScsiIfEntry ::= SEQUENCE {
    cucsVnicScsiIfInstanceId                                         CucsManagedObjectId,
    cucsVnicScsiIfDn                                                 CucsManagedObjectDn,
    cucsVnicScsiIfRn                                                 SnmpAdminString,
    cucsVnicScsiIfAddr                                               Unsigned64,
    cucsVnicScsiIfName                                               SnmpAdminString,
    cucsVnicScsiIfOperState                                          CucsVnicIfOperState,
    cucsVnicScsiIfOwner                                              CucsVnicConnectionOwner,
    cucsVnicScsiIfSwitchId                                           CucsNetworkSwitchId,
    cucsVnicScsiIfType                                               CucsVnicAScsiIfType,
    cucsVnicScsiIfVnet                                               Gauge32
}

cucsVnicScsiIfInstanceId OBJECT-TYPE
    SYNTAX       CucsManagedObjectId
    MAX-ACCESS   not-accessible
    STATUS       current
    DESCRIPTION
        "Instance identifier of the managed object."
    ::= { cucsVnicScsiIfEntry 1 }

cucsVnicScsiIfDn OBJECT-TYPE
    SYNTAX       CucsManagedObjectDn
    MAX-ACCESS   read-only
    STATUS       current
    DESCRIPTION
        "Cisco UCS vnic:ScsiIf:dn managed object property"
    ::= { cucsVnicScsiIfEntry 2 }

cucsVnicScsiIfRn OBJECT-TYPE
    SYNTAX       SnmpAdminString
    MAX-ACCESS   read-only
    STATUS       current
    DESCRIPTION
        "Cisco UCS vnic:ScsiIf:rn managed object property"
    ::= { cucsVnicScsiIfEntry 3 }

cucsVnicScsiIfAddr OBJECT-TYPE
    SYNTAX       Unsigned64
    MAX-ACCESS   read-only
    STATUS       current
    DESCRIPTION
        "Cisco UCS vnic:ScsiIf:addr managed object property"
    ::= { cucsVnicScsiIfEntry 4 }

cucsVnicScsiIfName OBJECT-TYPE
    SYNTAX       SnmpAdminString
    MAX-ACCESS   read-only
    STATUS       current
    DESCRIPTION
        "Cisco UCS vnic:ScsiIf:name managed object property"
    ::= { cucsVnicScsiIfEntry 5 }

cucsVnicScsiIfOperState OBJECT-TYPE
    SYNTAX       CucsVnicIfOperState
    MAX-ACCESS   read-only
    STATUS       current
    DESCRIPTION
        "Cisco UCS vnic:ScsiIf:operState managed object property"
    ::= { cucsVnicScsiIfEntry 6 }

cucsVnicScsiIfOwner OBJECT-TYPE
    SYNTAX       CucsVnicConnectionOwner
    MAX-ACCESS   read-only
    STATUS       current
    DESCRIPTION
        "Cisco UCS vnic:ScsiIf:owner managed object property"
    ::= { cucsVnicScsiIfEntry 7 }

cucsVnicScsiIfSwitchId OBJECT-TYPE
    SYNTAX       CucsNetworkSwitchId
    MAX-ACCESS   read-only
    STATUS       current
    DESCRIPTION
        "Cisco UCS vnic:ScsiIf:switchId managed object property"
    ::= { cucsVnicScsiIfEntry 8 }

cucsVnicScsiIfType OBJECT-TYPE
    SYNTAX       CucsVnicAScsiIfType
    MAX-ACCESS   read-only
    STATUS       current
    DESCRIPTION
        "Cisco UCS vnic:ScsiIf:type managed object property"
    ::= { cucsVnicScsiIfEntry 9 }

cucsVnicScsiIfVnet OBJECT-TYPE
    SYNTAX       Gauge32
    MAX-ACCESS   read-only
    STATUS       current
    DESCRIPTION
        "Cisco UCS vnic:ScsiIf:vnet managed object property"
    ::= { cucsVnicScsiIfEntry 10 }

cucsVnicVlanTable OBJECT-TYPE
    SYNTAX           SEQUENCE OF CucsVnicVlanEntry
    MAX-ACCESS       not-accessible
    STATUS           current
    DESCRIPTION
        "Cisco UCS vnic:Vlan managed object table"
    ::= { cucsVnicObjects 45 }

cucsVnicVlanEntry OBJECT-TYPE
    SYNTAX           CucsVnicVlanEntry
    MAX-ACCESS       not-accessible
    STATUS           current
    DESCRIPTION
        "Entry for the cucsVnicVlanTable table."
    INDEX { cucsVnicVlanInstanceId }
    ::= { cucsVnicVlanTable 1 }

CucsVnicVlanEntry ::= SEQUENCE {
    cucsVnicVlanInstanceId                                           CucsManagedObjectId,
    cucsVnicVlanDn                                                   CucsManagedObjectDn,
    cucsVnicVlanRn                                                   SnmpAdminString,
    cucsVnicVlanFltAggr                                              Unsigned64,
    cucsVnicVlanName                                                 SnmpAdminString,
    cucsVnicVlanOperState                                            CucsVnicIfOperState,
    cucsVnicVlanOwner                                                CucsVnicConnectionOwner,
    cucsVnicVlanSwitchId                                             CucsNetworkSwitchId,
    cucsVnicVlanType                                                 CucsVnicConnectionType,
    cucsVnicVlanVlanName                                             SnmpAdminString,
    cucsVnicVlanVnet                                                 Gauge32
}

cucsVnicVlanInstanceId OBJECT-TYPE
    SYNTAX       CucsManagedObjectId
    MAX-ACCESS   not-accessible
    STATUS       current
    DESCRIPTION
        "Instance identifier of the managed object."
    ::= { cucsVnicVlanEntry 1 }

cucsVnicVlanDn OBJECT-TYPE
    SYNTAX       CucsManagedObjectDn
    MAX-ACCESS   read-only
    STATUS       current
    DESCRIPTION
        "Cisco UCS vnic:Vlan:dn managed object property"
    ::= { cucsVnicVlanEntry 2 }

cucsVnicVlanRn OBJECT-TYPE
    SYNTAX       SnmpAdminString
    MAX-ACCESS   read-only
    STATUS       current
    DESCRIPTION
        "Cisco UCS vnic:Vlan:rn managed object property"
    ::= { cucsVnicVlanEntry 3 }

cucsVnicVlanFltAggr OBJECT-TYPE
    SYNTAX       Unsigned64
    MAX-ACCESS   read-only
    STATUS       current
    DESCRIPTION
        "Cisco UCS vnic:Vlan:fltAggr managed object property"
    ::= { cucsVnicVlanEntry 4 }

cucsVnicVlanName OBJECT-TYPE
    SYNTAX       SnmpAdminString
    MAX-ACCESS   read-only
    STATUS       current
    DESCRIPTION
        "Cisco UCS vnic:Vlan:name managed object property"
    ::= { cucsVnicVlanEntry 5 }

cucsVnicVlanOperState OBJECT-TYPE
    SYNTAX       CucsVnicIfOperState
    MAX-ACCESS   read-only
    STATUS       current
    DESCRIPTION
        "Cisco UCS vnic:Vlan:operState managed object property"
    ::= { cucsVnicVlanEntry 6 }

cucsVnicVlanOwner OBJECT-TYPE
    SYNTAX       CucsVnicConnectionOwner
    MAX-ACCESS   read-only
    STATUS       current
    DESCRIPTION
        "Cisco UCS vnic:Vlan:owner managed object property"
    ::= { cucsVnicVlanEntry 7 }

cucsVnicVlanSwitchId OBJECT-TYPE
    SYNTAX       CucsNetworkSwitchId
    MAX-ACCESS   read-only
    STATUS       current
    DESCRIPTION
        "Cisco UCS vnic:Vlan:switchId managed object property"
    ::= { cucsVnicVlanEntry 8 }

cucsVnicVlanType OBJECT-TYPE
    SYNTAX       CucsVnicConnectionType
    MAX-ACCESS   read-only
    STATUS       current
    DESCRIPTION
        "Cisco UCS vnic:Vlan:type managed object property"
    ::= { cucsVnicVlanEntry 9 }

cucsVnicVlanVlanName OBJECT-TYPE
    SYNTAX       SnmpAdminString
    MAX-ACCESS   read-only
    STATUS       current
    DESCRIPTION
        "Cisco UCS vnic:Vlan:vlanName managed object property"
    ::= { cucsVnicVlanEntry 10 }

cucsVnicVlanVnet OBJECT-TYPE
    SYNTAX       Gauge32
    MAX-ACCESS   read-only
    STATUS       current
    DESCRIPTION
        "Cisco UCS vnic:Vlan:vnet managed object property"
    ::= { cucsVnicVlanEntry 11 }

END
