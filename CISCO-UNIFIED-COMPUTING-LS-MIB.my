-- *********************************************************************
-- CISCO-UNIFIED-COMPUTING-LS-MIB.my
-- 
-- MIB representation of the Cisco Unified Computing System
-- LS management information model package
-- 
-- Created September 2011 by Charles Bullis
-- 
-- Copyright (c) 2005-2011 Cisco Systems, Inc. All rights reserved.
-- 
-- *********************************************************************

CISCO-UNIFIED-COMPUTING-LS-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsConditionRemoteInvRslt,
    CucsFsmCompletion,
    CucsLsAgentCapability,
    CucsLsAgentMode,
    CucsLsApply,
    CucsLsAssignment,
    CucsLsAssocState,
    CucsLsComputeBindingOperState,
    CucsLsConfigIssues,
    CucsLsConfigState,
    CucsLsOperState,
    CucsLsOwner,
    CucsLsPowerState,
    CucsLsServerFsmTaskFlags,
    CucsLsServerFsmTaskItem,
    CucsLsType,
    CucsVnicExternalMgmtIPMode
        FROM CISCO-UNIFIED-COMPUTING-TC-MIB;

cucsLsObjects MODULE-IDENTITY
    LAST-UPDATED    "201109150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        LS management information model package"
    ::= { ciscoUnifiedComputingMIBObjects 26 }

cucsLsAgentPolicyTable OBJECT-TYPE
    SYNTAX           SEQUENCE OF CucsLsAgentPolicyEntry
    MAX-ACCESS       not-accessible
    STATUS           current
    DESCRIPTION
        "Cisco UCS ls:AgentPolicy managed object table"
    ::= { cucsLsObjects 1 }

cucsLsAgentPolicyEntry OBJECT-TYPE
    SYNTAX           CucsLsAgentPolicyEntry
    MAX-ACCESS       not-accessible
    STATUS           current
    DESCRIPTION
        "Entry for the cucsLsAgentPolicyTable table."
    INDEX { cucsLsAgentPolicyInstanceId }
    ::= { cucsLsAgentPolicyTable 1 }

CucsLsAgentPolicyEntry ::= SEQUENCE {
    cucsLsAgentPolicyInstanceId                                      CucsManagedObjectId,
    cucsLsAgentPolicyDn                                              CucsManagedObjectDn,
    cucsLsAgentPolicyRn                                              SnmpAdminString,
    cucsLsAgentPolicyCapability                                      CucsLsAgentCapability,
    cucsLsAgentPolicyDescr                                           SnmpAdminString,
    cucsLsAgentPolicyIntId                                           SnmpAdminString,
    cucsLsAgentPolicyMode                                            CucsLsAgentMode,
    cucsLsAgentPolicyName                                            SnmpAdminString
}

cucsLsAgentPolicyInstanceId OBJECT-TYPE
    SYNTAX       CucsManagedObjectId
    MAX-ACCESS   not-accessible
    STATUS       current
    DESCRIPTION
        "Instance identifier of the managed object."
    ::= { cucsLsAgentPolicyEntry 1 }

cucsLsAgentPolicyDn OBJECT-TYPE
    SYNTAX       CucsManagedObjectDn
    MAX-ACCESS   read-only
    STATUS       current
    DESCRIPTION
        "Cisco UCS ls:AgentPolicy:dn managed object property"
    ::= { cucsLsAgentPolicyEntry 2 }

cucsLsAgentPolicyRn OBJECT-TYPE
    SYNTAX       SnmpAdminString
    MAX-ACCESS   read-only
    STATUS       current
    DESCRIPTION
        "Cisco UCS ls:AgentPolicy:rn managed object property"
    ::= { cucsLsAgentPolicyEntry 3 }

cucsLsAgentPolicyCapability OBJECT-TYPE
    SYNTAX       CucsLsAgentCapability
    MAX-ACCESS   read-only
    STATUS       current
    DESCRIPTION
        "Cisco UCS ls:AgentPolicy:capability managed object property"
    ::= { cucsLsAgentPolicyEntry 4 }

cucsLsAgentPolicyDescr OBJECT-TYPE
    SYNTAX       SnmpAdminString
    MAX-ACCESS   read-only
    STATUS       current
    DESCRIPTION
        "Cisco UCS ls:AgentPolicy:descr managed object property"
    ::= { cucsLsAgentPolicyEntry 5 }

cucsLsAgentPolicyIntId OBJECT-TYPE
    SYNTAX       SnmpAdminString
    MAX-ACCESS   read-only
    STATUS       current
    DESCRIPTION
        "Cisco UCS ls:AgentPolicy:intId managed object property"
    ::= { cucsLsAgentPolicyEntry 6 }

cucsLsAgentPolicyMode OBJECT-TYPE
    SYNTAX       CucsLsAgentMode
    MAX-ACCESS   read-only
    STATUS       current
    DESCRIPTION
        "Cisco UCS ls:AgentPolicy:mode managed object property"
    ::= { cucsLsAgentPolicyEntry 7 }

cucsLsAgentPolicyName OBJECT-TYPE
    SYNTAX       SnmpAdminString
    MAX-ACCESS   read-only
    STATUS       current
    DESCRIPTION
        "Cisco UCS ls:AgentPolicy:name managed object property"
    ::= { cucsLsAgentPolicyEntry 8 }

cucsLsBindingTable OBJECT-TYPE
    SYNTAX           SEQUENCE OF CucsLsBindingEntry
    MAX-ACCESS       not-accessible
    STATUS           current
    DESCRIPTION
        "Cisco UCS ls:Binding managed object table"
    ::= { cucsLsObjects 2 }

cucsLsBindingEntry OBJECT-TYPE
    SYNTAX           CucsLsBindingEntry
    MAX-ACCESS       not-accessible
    STATUS           current
    DESCRIPTION
        "Entry for the cucsLsBindingTable table."
    INDEX { cucsLsBindingInstanceId }
    ::= { cucsLsBindingTable 1 }

CucsLsBindingEntry ::= SEQUENCE {
    cucsLsBindingInstanceId                                          CucsManagedObjectId,
    cucsLsBindingDn                                                  CucsManagedObjectDn,
    cucsLsBindingRn                                                  SnmpAdminString,
    cucsLsBindingComputeEpDn                                         SnmpAdminString,
    cucsLsBindingName                                                SnmpAdminString,
    cucsLsBindingPnDn                                                SnmpAdminString,
    cucsLsBindingRestrictMigration                                   TruthValue,
    cucsLsBindingAssignedToDn                                        SnmpAdminString,
    cucsLsBindingIssues                                              CucsLsConfigIssues,
    cucsLsBindingOperState                                           CucsLsComputeBindingOperState
}

cucsLsBindingInstanceId OBJECT-TYPE
    SYNTAX       CucsManagedObjectId
    MAX-ACCESS   not-accessible
    STATUS       current
    DESCRIPTION
        "Instance identifier of the managed object."
    ::= { cucsLsBindingEntry 1 }

cucsLsBindingDn OBJECT-TYPE
    SYNTAX       CucsManagedObjectDn
    MAX-ACCESS   read-only
    STATUS       current
    DESCRIPTION
        "Cisco UCS ls:Binding:dn managed object property"
    ::= { cucsLsBindingEntry 2 }

cucsLsBindingRn OBJECT-TYPE
    SYNTAX       SnmpAdminString
    MAX-ACCESS   read-only
    STATUS       current
    DESCRIPTION
        "Cisco UCS ls:Binding:rn managed object property"
    ::= { cucsLsBindingEntry 3 }

cucsLsBindingComputeEpDn OBJECT-TYPE
    SYNTAX       SnmpAdminString
    MAX-ACCESS   read-only
    STATUS       current
    DESCRIPTION
        "Cisco UCS ls:Binding:computeEpDn managed object property"
    ::= { cucsLsBindingEntry 4 }

cucsLsBindingName OBJECT-TYPE
    SYNTAX       SnmpAdminString
    MAX-ACCESS   read-only
    STATUS       current
    DESCRIPTION
        "Cisco UCS ls:Binding:name managed object property"
    ::= { cucsLsBindingEntry 5 }

cucsLsBindingPnDn OBJECT-TYPE
    SYNTAX       SnmpAdminString
    MAX-ACCESS   read-only
    STATUS       current
    DESCRIPTION
        "Cisco UCS ls:Binding:pnDn managed object property"
    ::= { cucsLsBindingEntry 6 }

cucsLsBindingRestrictMigration OBJECT-TYPE
    SYNTAX       TruthValue
    MAX-ACCESS   read-only
    STATUS       current
    DESCRIPTION
        "Cisco UCS ls:Binding:restrictMigration managed object property"
    ::= { cucsLsBindingEntry 7 }

cucsLsBindingAssignedToDn OBJECT-TYPE
    SYNTAX       SnmpAdminString
    MAX-ACCESS   read-only
    STATUS       current
    DESCRIPTION
        "Cisco UCS ls:Binding:assignedToDn managed object property"
    ::= { cucsLsBindingEntry 8 }

cucsLsBindingIssues OBJECT-TYPE
    SYNTAX       CucsLsConfigIssues
    MAX-ACCESS   read-only
    STATUS       current
    DESCRIPTION
        "Cisco UCS ls:Binding:issues managed object property"
    ::= { cucsLsBindingEntry 9 }

cucsLsBindingOperState OBJECT-TYPE
    SYNTAX       CucsLsComputeBindingOperState
    MAX-ACCESS   read-only
    STATUS       current
    DESCRIPTION
        "Cisco UCS ls:Binding:operState managed object property"
    ::= { cucsLsBindingEntry 10 }

cucsLsPowerTable OBJECT-TYPE
    SYNTAX           SEQUENCE OF CucsLsPowerEntry
    MAX-ACCESS       not-accessible
    STATUS           current
    DESCRIPTION
        "Cisco UCS ls:Power managed object table"
    ::= { cucsLsObjects 3 }

cucsLsPowerEntry OBJECT-TYPE
    SYNTAX           CucsLsPowerEntry
    MAX-ACCESS       not-accessible
    STATUS           current
    DESCRIPTION
        "Entry for the cucsLsPowerTable table."
    INDEX { cucsLsPowerInstanceId }
    ::= { cucsLsPowerTable 1 }

CucsLsPowerEntry ::= SEQUENCE {
    cucsLsPowerInstanceId                                            CucsManagedObjectId,
    cucsLsPowerDn                                                    CucsManagedObjectDn,
    cucsLsPowerRn                                                    SnmpAdminString,
    cucsLsPowerState                                                 CucsLsPowerState
}

cucsLsPowerInstanceId OBJECT-TYPE
    SYNTAX       CucsManagedObjectId
    MAX-ACCESS   not-accessible
    STATUS       current
    DESCRIPTION
        "Instance identifier of the managed object."
    ::= { cucsLsPowerEntry 1 }

cucsLsPowerDn OBJECT-TYPE
    SYNTAX       CucsManagedObjectDn
    MAX-ACCESS   read-only
    STATUS       current
    DESCRIPTION
        "Cisco UCS ls:Power:dn managed object property"
    ::= { cucsLsPowerEntry 2 }

cucsLsPowerRn OBJECT-TYPE
    SYNTAX       SnmpAdminString
    MAX-ACCESS   read-only
    STATUS       current
    DESCRIPTION
        "Cisco UCS ls:Power:rn managed object property"
    ::= { cucsLsPowerEntry 3 }

cucsLsPowerState OBJECT-TYPE
    SYNTAX       CucsLsPowerState
    MAX-ACCESS   read-only
    STATUS       current
    DESCRIPTION
        "Cisco UCS ls:Power:state managed object property"
    ::= { cucsLsPowerEntry 4 }

cucsLsRequirementTable OBJECT-TYPE
    SYNTAX           SEQUENCE OF CucsLsRequirementEntry
    MAX-ACCESS       not-accessible
    STATUS           current
    DESCRIPTION
        "Cisco UCS ls:Requirement managed object table"
    ::= { cucsLsObjects 4 }

cucsLsRequirementEntry OBJECT-TYPE
    SYNTAX           CucsLsRequirementEntry
    MAX-ACCESS       not-accessible
    STATUS           current
    DESCRIPTION
        "Entry for the cucsLsRequirementTable table."
    INDEX { cucsLsRequirementInstanceId }
    ::= { cucsLsRequirementTable 1 }

CucsLsRequirementEntry ::= SEQUENCE {
    cucsLsRequirementInstanceId                                      CucsManagedObjectId,
    cucsLsRequirementDn                                              CucsManagedObjectDn,
    cucsLsRequirementRn                                              SnmpAdminString,
    cucsLsRequirementComputeEpDn                                     SnmpAdminString,
    cucsLsRequirementName                                            SnmpAdminString,
    cucsLsRequirementPnPoolDn                                        SnmpAdminString,
    cucsLsRequirementQualifier                                       SnmpAdminString,
    cucsLsRequirementRestrictMigration                               TruthValue,
    cucsLsRequirementAssignedToDn                                    SnmpAdminString,
    cucsLsRequirementIssues                                          CucsLsConfigIssues,
    cucsLsRequirementOperState                                       CucsLsComputeBindingOperState,
    cucsLsRequirementPnDn                                            SnmpAdminString
}

cucsLsRequirementInstanceId OBJECT-TYPE
    SYNTAX       CucsManagedObjectId
    MAX-ACCESS   not-accessible
    STATUS       current
    DESCRIPTION
        "Instance identifier of the managed object."
    ::= { cucsLsRequirementEntry 1 }

cucsLsRequirementDn OBJECT-TYPE
    SYNTAX       CucsManagedObjectDn
    MAX-ACCESS   read-only
    STATUS       current
    DESCRIPTION
        "Cisco UCS ls:Requirement:dn managed object property"
    ::= { cucsLsRequirementEntry 2 }

cucsLsRequirementRn OBJECT-TYPE
    SYNTAX       SnmpAdminString
    MAX-ACCESS   read-only
    STATUS       current
    DESCRIPTION
        "Cisco UCS ls:Requirement:rn managed object property"
    ::= { cucsLsRequirementEntry 3 }

cucsLsRequirementComputeEpDn OBJECT-TYPE
    SYNTAX       SnmpAdminString
    MAX-ACCESS   read-only
    STATUS       current
    DESCRIPTION
        "Cisco UCS ls:Requirement:computeEpDn managed object property"
    ::= { cucsLsRequirementEntry 4 }

cucsLsRequirementName OBJECT-TYPE
    SYNTAX       SnmpAdminString
    MAX-ACCESS   read-only
    STATUS       current
    DESCRIPTION
        "Cisco UCS ls:Requirement:name managed object property"
    ::= { cucsLsRequirementEntry 5 }

cucsLsRequirementPnPoolDn OBJECT-TYPE
    SYNTAX       SnmpAdminString
    MAX-ACCESS   read-only
    STATUS       current
    DESCRIPTION
        "Cisco UCS ls:Requirement:pnPoolDn managed object property"
    ::= { cucsLsRequirementEntry 6 }

cucsLsRequirementQualifier OBJECT-TYPE
    SYNTAX       SnmpAdminString
    MAX-ACCESS   read-only
    STATUS       current
    DESCRIPTION
        "Cisco UCS ls:Requirement:qualifier managed object property"
    ::= { cucsLsRequirementEntry 7 }

cucsLsRequirementRestrictMigration OBJECT-TYPE
    SYNTAX       TruthValue
    MAX-ACCESS   read-only
    STATUS       current
    DESCRIPTION
        "Cisco UCS ls:Requirement:restrictMigration managed
        object property"
    ::= { cucsLsRequirementEntry 8 }

cucsLsRequirementAssignedToDn OBJECT-TYPE
    SYNTAX       SnmpAdminString
    MAX-ACCESS   read-only
    STATUS       current
    DESCRIPTION
        "Cisco UCS ls:Requirement:assignedToDn managed object property"
    ::= { cucsLsRequirementEntry 9 }

cucsLsRequirementIssues OBJECT-TYPE
    SYNTAX       CucsLsConfigIssues
    MAX-ACCESS   read-only
    STATUS       current
    DESCRIPTION
        "Cisco UCS ls:Requirement:issues managed object property"
    ::= { cucsLsRequirementEntry 10 }

cucsLsRequirementOperState OBJECT-TYPE
    SYNTAX       CucsLsComputeBindingOperState
    MAX-ACCESS   read-only
    STATUS       current
    DESCRIPTION
        "Cisco UCS ls:Requirement:operState managed object property"
    ::= { cucsLsRequirementEntry 11 }

cucsLsRequirementPnDn OBJECT-TYPE
    SYNTAX       SnmpAdminString
    MAX-ACCESS   read-only
    STATUS       current
    DESCRIPTION
        "Cisco UCS ls:Requirement:pnDn managed object property"
    ::= { cucsLsRequirementEntry 12 }

cucsLsServerTable OBJECT-TYPE
    SYNTAX           SEQUENCE OF CucsLsServerEntry
    MAX-ACCESS       not-accessible
    STATUS           current
    DESCRIPTION
        "Cisco UCS ls:Server managed object table"
    ::= { cucsLsObjects 5 }

cucsLsServerEntry OBJECT-TYPE
    SYNTAX           CucsLsServerEntry
    MAX-ACCESS       not-accessible
    STATUS           current
    DESCRIPTION
        "Entry for the cucsLsServerTable table."
    INDEX { cucsLsServerInstanceId }
    ::= { cucsLsServerTable 1 }

CucsLsServerEntry ::= SEQUENCE {
    cucsLsServerInstanceId                                           CucsManagedObjectId,
    cucsLsServerDn                                                   CucsManagedObjectDn,
    cucsLsServerRn                                                   SnmpAdminString,
    cucsLsServerAgentPolicyName                                      SnmpAdminString,
    cucsLsServerAssignState                                          CucsLsAssignment,
    cucsLsServerAssocState                                           CucsLsAssocState,
    cucsLsServerBiosProfileName                                      SnmpAdminString,
    cucsLsServerBootPolicyName                                       SnmpAdminString,
    cucsLsServerConfigQualifier                                      CucsLsConfigIssues,
    cucsLsServerConfigState                                          CucsLsConfigState,
    cucsLsServerDescr                                                SnmpAdminString,
    cucsLsServerDynamicConPolicyName                                 SnmpAdminString,
    cucsLsServerExtIPState                                           CucsVnicExternalMgmtIPMode,
    cucsLsServerFltAggr                                              Unsigned64,
    cucsLsServerHostFwPolicyName                                     SnmpAdminString,
    cucsLsServerIdentPoolName                                        SnmpAdminString,
    cucsLsServerIntId                                                SnmpAdminString,
    cucsLsServerLocalDiskPolicyName                                  SnmpAdminString,
    cucsLsServerMaintPolicyName                                      SnmpAdminString,
    cucsLsServerMgmtAccessPolicyName                                 SnmpAdminString,
    cucsLsServerMgmtFwPolicyName                                     SnmpAdminString,
    cucsLsServerName                                                 SnmpAdminString,
    cucsLsServerOperBiosProfileName                                  SnmpAdminString,
    cucsLsServerOperBootPolicyName                                   SnmpAdminString,
    cucsLsServerOperDynamicConPolicyName                             SnmpAdminString,
    cucsLsServerOperHostFwPolicyName                                 SnmpAdminString,
    cucsLsServerOperIdentPoolName                                    SnmpAdminString,
    cucsLsServerOperLocalDiskPolicyName                              SnmpAdminString,
    cucsLsServerOperMgmtAccessPolicyName                             SnmpAdminString,
    cucsLsServerOperMgmtFwPolicyName                                 SnmpAdminString,
    cucsLsServerOperScrubPolicyName                                  SnmpAdminString,
    cucsLsServerOperSolPolicyName                                    SnmpAdminString,
    cucsLsServerOperSrcTemplName                                     SnmpAdminString,
    cucsLsServerOperState                                            CucsLsOperState,
    cucsLsServerOperStatsPolicyName                                  SnmpAdminString,
    cucsLsServerOperVconProfileName                                  SnmpAdminString,
    cucsLsServerOwner                                                CucsLsOwner,
    cucsLsServerFsmFlags                                             SnmpAdminString,
    cucsLsServerPnDn                                                 SnmpAdminString,
    cucsLsServerPowerPolicyName                                      SnmpAdminString,
    cucsLsServerScrubPolicyName                                      SnmpAdminString,
    cucsLsServerSolPolicyName                                        SnmpAdminString,
    cucsLsServerSrcTemplName                                         SnmpAdminString,
    cucsLsServerStatsPolicyName                                      SnmpAdminString,
    cucsLsServerType                                                 CucsLsType,
    cucsLsServerUsrLbl                                               SnmpAdminString,
    cucsLsServerUuid                                                 SnmpAdminString,
    cucsLsServerUuidSuffix                                           Unsigned64,
    cucsLsServerVconProfileName                                      SnmpAdminString,
    cucsLsServerFsmDescr                                             SnmpAdminString,
    cucsLsServerFsmPrev                                              SnmpAdminString,
    cucsLsServerFsmProgr                                             Gauge32,
    cucsLsServerFsmRmtInvErrCode                                     Gauge32,
    cucsLsServerFsmRmtInvErrDescr                                    SnmpAdminString,
    cucsLsServerFsmRmtInvRslt                                        CucsConditionRemoteInvRslt,
    cucsLsServerFsmStageDescr                                        SnmpAdminString,
    cucsLsServerFsmStamp                                             DateAndTime,
    cucsLsServerFsmStatus                                            SnmpAdminString,
    cucsLsServerFsmTry                                               Gauge32,
    cucsLsServerOperMaintPolicyName                                  SnmpAdminString,
    cucsLsServerOperPowerPolicyName                                  SnmpAdminString
}

cucsLsServerInstanceId OBJECT-TYPE
    SYNTAX       CucsManagedObjectId
    MAX-ACCESS   not-accessible
    STATUS       current
    DESCRIPTION
        "Instance identifier of the managed object."
    ::= { cucsLsServerEntry 1 }

cucsLsServerDn OBJECT-TYPE
    SYNTAX       CucsManagedObjectDn
    MAX-ACCESS   read-only
    STATUS       current
    DESCRIPTION
        "Cisco UCS ls:Server:dn managed object property"
    ::= { cucsLsServerEntry 2 }

cucsLsServerRn OBJECT-TYPE
    SYNTAX       SnmpAdminString
    MAX-ACCESS   read-only
    STATUS       current
    DESCRIPTION
        "Cisco UCS ls:Server:rn managed object property"
    ::= { cucsLsServerEntry 3 }

cucsLsServerAgentPolicyName OBJECT-TYPE
    SYNTAX       SnmpAdminString
    MAX-ACCESS   read-only
    STATUS       current
    DESCRIPTION
        "Cisco UCS ls:Server:agentPolicyName managed object property"
    ::= { cucsLsServerEntry 4 }

cucsLsServerAssignState OBJECT-TYPE
    SYNTAX       CucsLsAssignment
    MAX-ACCESS   read-only
    STATUS       current
    DESCRIPTION
        "Cisco UCS ls:Server:assignState managed object property"
    ::= { cucsLsServerEntry 5 }

cucsLsServerAssocState OBJECT-TYPE
    SYNTAX       CucsLsAssocState
    MAX-ACCESS   read-only
    STATUS       current
    DESCRIPTION
        "Cisco UCS ls:Server:assocState managed object property"
    ::= { cucsLsServerEntry 6 }

cucsLsServerBiosProfileName OBJECT-TYPE
    SYNTAX       SnmpAdminString
    MAX-ACCESS   read-only
    STATUS       current
    DESCRIPTION
        "Cisco UCS ls:Server:biosProfileName managed object property"
    ::= { cucsLsServerEntry 7 }

cucsLsServerBootPolicyName OBJECT-TYPE
    SYNTAX       SnmpAdminString
    MAX-ACCESS   read-only
    STATUS       current
    DESCRIPTION
        "Cisco UCS ls:Server:bootPolicyName managed object property"
    ::= { cucsLsServerEntry 8 }

cucsLsServerConfigQualifier OBJECT-TYPE
    SYNTAX       CucsLsConfigIssues
    MAX-ACCESS   read-only
    STATUS       current
    DESCRIPTION
        "Cisco UCS ls:Server:configQualifier managed object property"
    ::= { cucsLsServerEntry 9 }

cucsLsServerConfigState OBJECT-TYPE
    SYNTAX       CucsLsConfigState
    MAX-ACCESS   read-only
    STATUS       current
    DESCRIPTION
        "Cisco UCS ls:Server:configState managed object property"
    ::= { cucsLsServerEntry 10 }

cucsLsServerDescr OBJECT-TYPE
    SYNTAX       SnmpAdminString
    MAX-ACCESS   read-only
    STATUS       current
    DESCRIPTION
        "Cisco UCS ls:Server:descr managed object property"
    ::= { cucsLsServerEntry 11 }

cucsLsServerDynamicConPolicyName OBJECT-TYPE
    SYNTAX       SnmpAdminString
    MAX-ACCESS   read-only
    STATUS       current
    DESCRIPTION
        "Cisco UCS ls:Server:dynamicConPolicyName managed object property"
    ::= { cucsLsServerEntry 12 }

cucsLsServerExtIPState OBJECT-TYPE
    SYNTAX       CucsVnicExternalMgmtIPMode
    MAX-ACCESS   read-only
    STATUS       current
    DESCRIPTION
        "Cisco UCS ls:Server:extIPState managed object property"
    ::= { cucsLsServerEntry 13 }

cucsLsServerFltAggr OBJECT-TYPE
    SYNTAX       Unsigned64
    MAX-ACCESS   read-only
    STATUS       current
    DESCRIPTION
        "Cisco UCS ls:Server:fltAggr managed object property"
    ::= { cucsLsServerEntry 14 }

cucsLsServerHostFwPolicyName OBJECT-TYPE
    SYNTAX       SnmpAdminString
    MAX-ACCESS   read-only
    STATUS       current
    DESCRIPTION
        "Cisco UCS ls:Server:hostFwPolicyName managed object property"
    ::= { cucsLsServerEntry 15 }

cucsLsServerIdentPoolName OBJECT-TYPE
    SYNTAX       SnmpAdminString
    MAX-ACCESS   read-only
    STATUS       current
    DESCRIPTION
        "Cisco UCS ls:Server:identPoolName managed object property"
    ::= { cucsLsServerEntry 16 }

cucsLsServerIntId OBJECT-TYPE
    SYNTAX       SnmpAdminString
    MAX-ACCESS   read-only
    STATUS       current
    DESCRIPTION
        "Cisco UCS ls:Server:intId managed object property"
    ::= { cucsLsServerEntry 17 }

cucsLsServerLocalDiskPolicyName OBJECT-TYPE
    SYNTAX       SnmpAdminString
    MAX-ACCESS   read-only
    STATUS       current
    DESCRIPTION
        "Cisco UCS ls:Server:localDiskPolicyName managed object property"
    ::= { cucsLsServerEntry 18 }

cucsLsServerMaintPolicyName OBJECT-TYPE
    SYNTAX       SnmpAdminString
    MAX-ACCESS   read-only
    STATUS       current
    DESCRIPTION
        "Cisco UCS ls:Server:maintPolicyName managed object property"
    ::= { cucsLsServerEntry 19 }

cucsLsServerMgmtAccessPolicyName OBJECT-TYPE
    SYNTAX       SnmpAdminString
    MAX-ACCESS   read-only
    STATUS       current
    DESCRIPTION
        "Cisco UCS ls:Server:mgmtAccessPolicyName managed object property"
    ::= { cucsLsServerEntry 20 }

cucsLsServerMgmtFwPolicyName OBJECT-TYPE
    SYNTAX       SnmpAdminString
    MAX-ACCESS   read-only
    STATUS       current
    DESCRIPTION
        "Cisco UCS ls:Server:mgmtFwPolicyName managed object property"
    ::= { cucsLsServerEntry 21 }

cucsLsServerName OBJECT-TYPE
    SYNTAX       SnmpAdminString
    MAX-ACCESS   read-only
    STATUS       current
    DESCRIPTION
        "Cisco UCS ls:Server:name managed object property"
    ::= { cucsLsServerEntry 22 }

cucsLsServerOperBiosProfileName OBJECT-TYPE
    SYNTAX       SnmpAdminString
    MAX-ACCESS   read-only
    STATUS       current
    DESCRIPTION
        "Cisco UCS ls:Server:operBiosProfileName managed object property"
    ::= { cucsLsServerEntry 23 }

cucsLsServerOperBootPolicyName OBJECT-TYPE
    SYNTAX       SnmpAdminString
    MAX-ACCESS   read-only
    STATUS       current
    DESCRIPTION
        "Cisco UCS ls:Server:operBootPolicyName managed object property"
    ::= { cucsLsServerEntry 24 }

cucsLsServerOperDynamicConPolicyName OBJECT-TYPE
    SYNTAX       SnmpAdminString
    MAX-ACCESS   read-only
    STATUS       current
    DESCRIPTION
        "Cisco UCS ls:Server:operDynamicConPolicyName managed
        object property"
    ::= { cucsLsServerEntry 25 }

cucsLsServerOperHostFwPolicyName OBJECT-TYPE
    SYNTAX       SnmpAdminString
    MAX-ACCESS   read-only
    STATUS       current
    DESCRIPTION
        "Cisco UCS ls:Server:operHostFwPolicyName managed object property"
    ::= { cucsLsServerEntry 26 }

cucsLsServerOperIdentPoolName OBJECT-TYPE
    SYNTAX       SnmpAdminString
    MAX-ACCESS   read-only
    STATUS       current
    DESCRIPTION
        "Cisco UCS ls:Server:operIdentPoolName managed object property"
    ::= { cucsLsServerEntry 27 }

cucsLsServerOperLocalDiskPolicyName OBJECT-TYPE
    SYNTAX       SnmpAdminString
    MAX-ACCESS   read-only
    STATUS       current
    DESCRIPTION
        "Cisco UCS ls:Server:operLocalDiskPolicyName managed
        object property"
    ::= { cucsLsServerEntry 28 }

cucsLsServerOperMgmtAccessPolicyName OBJECT-TYPE
    SYNTAX       SnmpAdminString
    MAX-ACCESS   read-only
    STATUS       current
    DESCRIPTION
        "Cisco UCS ls:Server:operMgmtAccessPolicyName managed
        object property"
    ::= { cucsLsServerEntry 29 }

cucsLsServerOperMgmtFwPolicyName OBJECT-TYPE
    SYNTAX       SnmpAdminString
    MAX-ACCESS   read-only
    STATUS       current
    DESCRIPTION
        "Cisco UCS ls:Server:operMgmtFwPolicyName managed object property"
    ::= { cucsLsServerEntry 30 }

cucsLsServerOperScrubPolicyName OBJECT-TYPE
    SYNTAX       SnmpAdminString
    MAX-ACCESS   read-only
    STATUS       current
    DESCRIPTION
        "Cisco UCS ls:Server:operScrubPolicyName managed object property"
    ::= { cucsLsServerEntry 31 }

cucsLsServerOperSolPolicyName OBJECT-TYPE
    SYNTAX       SnmpAdminString
    MAX-ACCESS   read-only
    STATUS       current
    DESCRIPTION
        "Cisco UCS ls:Server:operSolPolicyName managed object property"
    ::= { cucsLsServerEntry 32 }

cucsLsServerOperSrcTemplName OBJECT-TYPE
    SYNTAX       SnmpAdminString
    MAX-ACCESS   read-only
    STATUS       current
    DESCRIPTION
        "Cisco UCS ls:Server:operSrcTemplName managed object property"
    ::= { cucsLsServerEntry 33 }

cucsLsServerOperState OBJECT-TYPE
    SYNTAX       CucsLsOperState
    MAX-ACCESS   read-only
    STATUS       current
    DESCRIPTION
        "Cisco UCS ls:Server:operState managed object property"
    ::= { cucsLsServerEntry 34 }

cucsLsServerOperStatsPolicyName OBJECT-TYPE
    SYNTAX       SnmpAdminString
    MAX-ACCESS   read-only
    STATUS       current
    DESCRIPTION
        "Cisco UCS ls:Server:operStatsPolicyName managed object property"
    ::= { cucsLsServerEntry 35 }

cucsLsServerOperVconProfileName OBJECT-TYPE
    SYNTAX       SnmpAdminString
    MAX-ACCESS   read-only
    STATUS       current
    DESCRIPTION
        "Cisco UCS ls:Server:operVconProfileName managed object property"
    ::= { cucsLsServerEntry 36 }

cucsLsServerOwner OBJECT-TYPE
    SYNTAX       CucsLsOwner
    MAX-ACCESS   read-only
    STATUS       current
    DESCRIPTION
        "Cisco UCS ls:Server:owner managed object property"
    ::= { cucsLsServerEntry 37 }

cucsLsServerFsmFlags OBJECT-TYPE
    SYNTAX       SnmpAdminString
    MAX-ACCESS   read-only
    STATUS       current
    DESCRIPTION
        "Cisco UCS ls:Server:fsmFlags managed object property"
    ::= { cucsLsServerEntry 38 }

cucsLsServerPnDn OBJECT-TYPE
    SYNTAX       SnmpAdminString
    MAX-ACCESS   read-only
    STATUS       current
    DESCRIPTION
        "Cisco UCS ls:Server:pnDn managed object property"
    ::= { cucsLsServerEntry 39 }

cucsLsServerPowerPolicyName OBJECT-TYPE
    SYNTAX       SnmpAdminString
    MAX-ACCESS   read-only
    STATUS       current
    DESCRIPTION
        "Cisco UCS ls:Server:powerPolicyName managed object property"
    ::= { cucsLsServerEntry 40 }

cucsLsServerScrubPolicyName OBJECT-TYPE
    SYNTAX       SnmpAdminString
    MAX-ACCESS   read-only
    STATUS       current
    DESCRIPTION
        "Cisco UCS ls:Server:scrubPolicyName managed object property"
    ::= { cucsLsServerEntry 41 }

cucsLsServerSolPolicyName OBJECT-TYPE
    SYNTAX       SnmpAdminString
    MAX-ACCESS   read-only
    STATUS       current
    DESCRIPTION
        "Cisco UCS ls:Server:solPolicyName managed object property"
    ::= { cucsLsServerEntry 42 }

cucsLsServerSrcTemplName OBJECT-TYPE
    SYNTAX       SnmpAdminString
    MAX-ACCESS   read-only
    STATUS       current
    DESCRIPTION
        "Cisco UCS ls:Server:srcTemplName managed object property"
    ::= { cucsLsServerEntry 43 }

cucsLsServerStatsPolicyName OBJECT-TYPE
    SYNTAX       SnmpAdminString
    MAX-ACCESS   read-only
    STATUS       current
    DESCRIPTION
        "Cisco UCS ls:Server:statsPolicyName managed object property"
    ::= { cucsLsServerEntry 44 }

cucsLsServerType OBJECT-TYPE
    SYNTAX       CucsLsType
    MAX-ACCESS   read-only
    STATUS       current
    DESCRIPTION
        "Cisco UCS ls:Server:type managed object property"
    ::= { cucsLsServerEntry 45 }

cucsLsServerUsrLbl OBJECT-TYPE
    SYNTAX       SnmpAdminString
    MAX-ACCESS   read-only
    STATUS       current
    DESCRIPTION
        "Cisco UCS ls:Server:usrLbl managed object property"
    ::= { cucsLsServerEntry 46 }

cucsLsServerUuid OBJECT-TYPE
    SYNTAX       SnmpAdminString
    MAX-ACCESS   read-only
    STATUS       current
    DESCRIPTION
        "Cisco UCS ls:Server:uuid managed object property"
    ::= { cucsLsServerEntry 47 }

cucsLsServerUuidSuffix OBJECT-TYPE
    SYNTAX       Unsigned64
    MAX-ACCESS   read-only
    STATUS       current
    DESCRIPTION
        "Cisco UCS ls:Server:uuidSuffix managed object property"
    ::= { cucsLsServerEntry 48 }

cucsLsServerVconProfileName OBJECT-TYPE
    SYNTAX       SnmpAdminString
    MAX-ACCESS   read-only
    STATUS       current
    DESCRIPTION
        "Cisco UCS ls:Server:vconProfileName managed object property"
    ::= { cucsLsServerEntry 49 }

cucsLsServerFsmDescr OBJECT-TYPE
    SYNTAX       SnmpAdminString
    MAX-ACCESS   read-only
    STATUS       current
    DESCRIPTION
        "Cisco UCS ls:Server:fsmDescr managed object property"
    ::= { cucsLsServerEntry 50 }

cucsLsServerFsmPrev OBJECT-TYPE
    SYNTAX       SnmpAdminString
    MAX-ACCESS   read-only
    STATUS       current
    DESCRIPTION
        "Cisco UCS ls:Server:fsmPrev managed object property"
    ::= { cucsLsServerEntry 51 }

cucsLsServerFsmProgr OBJECT-TYPE
    SYNTAX       Gauge32
    MAX-ACCESS   read-only
    STATUS       current
    DESCRIPTION
        "Cisco UCS ls:Server:fsmProgr managed object property"
    ::= { cucsLsServerEntry 52 }

cucsLsServerFsmRmtInvErrCode OBJECT-TYPE
    SYNTAX       Gauge32
    MAX-ACCESS   read-only
    STATUS       current
    DESCRIPTION
        "Cisco UCS ls:Server:fsmRmtInvErrCode managed object property"
    ::= { cucsLsServerEntry 53 }

cucsLsServerFsmRmtInvErrDescr OBJECT-TYPE
    SYNTAX       SnmpAdminString
    MAX-ACCESS   read-only
    STATUS       current
    DESCRIPTION
        "Cisco UCS ls:Server:fsmRmtInvErrDescr managed object property"
    ::= { cucsLsServerEntry 54 }

cucsLsServerFsmRmtInvRslt OBJECT-TYPE
    SYNTAX       CucsConditionRemoteInvRslt
    MAX-ACCESS   read-only
    STATUS       current
    DESCRIPTION
        "Cisco UCS ls:Server:fsmRmtInvRslt managed object property"
    ::= { cucsLsServerEntry 55 }

cucsLsServerFsmStageDescr OBJECT-TYPE
    SYNTAX       SnmpAdminString
    MAX-ACCESS   read-only
    STATUS       current
    DESCRIPTION
        "Cisco UCS ls:Server:fsmStageDescr managed object property"
    ::= { cucsLsServerEntry 56 }

cucsLsServerFsmStamp OBJECT-TYPE
    SYNTAX       DateAndTime
    MAX-ACCESS   read-only
    STATUS       current
    DESCRIPTION
        "Cisco UCS ls:Server:fsmStamp managed object property"
    ::= { cucsLsServerEntry 57 }

cucsLsServerFsmStatus OBJECT-TYPE
    SYNTAX       SnmpAdminString
    MAX-ACCESS   read-only
    STATUS       current
    DESCRIPTION
        "Cisco UCS ls:Server:fsmStatus managed object property"
    ::= { cucsLsServerEntry 58 }

cucsLsServerFsmTry OBJECT-TYPE
    SYNTAX       Gauge32
    MAX-ACCESS   read-only
    STATUS       current
    DESCRIPTION
        "Cisco UCS ls:Server:fsmTry managed object property"
    ::= { cucsLsServerEntry 59 }

cucsLsServerOperMaintPolicyName OBJECT-TYPE
    SYNTAX       SnmpAdminString
    MAX-ACCESS   read-only
    STATUS       current
    DESCRIPTION
        "Cisco UCS ls:Server:operMaintPolicyName managed object property"
    ::= { cucsLsServerEntry 60 }

cucsLsServerOperPowerPolicyName OBJECT-TYPE
    SYNTAX       SnmpAdminString
    MAX-ACCESS   read-only
    STATUS       current
    DESCRIPTION
        "Cisco UCS ls:Server:operPowerPolicyName managed object property"
    ::= { cucsLsServerEntry 61 }

cucsLsServerAssocCtxTable OBJECT-TYPE
    SYNTAX           SEQUENCE OF CucsLsServerAssocCtxEntry
    MAX-ACCESS       not-accessible
    STATUS           current
    DESCRIPTION
        "Cisco UCS ls:ServerAssocCtx managed object table"
    ::= { cucsLsObjects 8 }

cucsLsServerAssocCtxEntry OBJECT-TYPE
    SYNTAX           CucsLsServerAssocCtxEntry
    MAX-ACCESS       not-accessible
    STATUS           current
    DESCRIPTION
        "Entry for the cucsLsServerAssocCtxTable table."
    INDEX { cucsLsServerAssocCtxInstanceId }
    ::= { cucsLsServerAssocCtxTable 1 }

CucsLsServerAssocCtxEntry ::= SEQUENCE {
    cucsLsServerAssocCtxInstanceId                                   CucsManagedObjectId,
    cucsLsServerAssocCtxDn                                           CucsManagedObjectDn,
    cucsLsServerAssocCtxRn                                           SnmpAdminString
}

cucsLsServerAssocCtxInstanceId OBJECT-TYPE
    SYNTAX       CucsManagedObjectId
    MAX-ACCESS   not-accessible
    STATUS       current
    DESCRIPTION
        "Instance identifier of the managed object."
    ::= { cucsLsServerAssocCtxEntry 1 }

cucsLsServerAssocCtxDn OBJECT-TYPE
    SYNTAX       CucsManagedObjectDn
    MAX-ACCESS   read-only
    STATUS       current
    DESCRIPTION
        "Cisco UCS ls:ServerAssocCtx:dn managed object property"
    ::= { cucsLsServerAssocCtxEntry 2 }

cucsLsServerAssocCtxRn OBJECT-TYPE
    SYNTAX       SnmpAdminString
    MAX-ACCESS   read-only
    STATUS       current
    DESCRIPTION
        "Cisco UCS ls:ServerAssocCtx:rn managed object property"
    ::= { cucsLsServerAssocCtxEntry 3 }

cucsLsServerFsmTaskTable OBJECT-TYPE
    SYNTAX           SEQUENCE OF CucsLsServerFsmTaskEntry
    MAX-ACCESS       not-accessible
    STATUS           current
    DESCRIPTION
        "Cisco UCS ls:ServerFsmTask managed object table"
    ::= { cucsLsObjects 7 }

cucsLsServerFsmTaskEntry OBJECT-TYPE
    SYNTAX           CucsLsServerFsmTaskEntry
    MAX-ACCESS       not-accessible
    STATUS           current
    DESCRIPTION
        "Entry for the cucsLsServerFsmTaskTable table."
    INDEX { cucsLsServerFsmTaskInstanceId }
    ::= { cucsLsServerFsmTaskTable 1 }

CucsLsServerFsmTaskEntry ::= SEQUENCE {
    cucsLsServerFsmTaskInstanceId                                    CucsManagedObjectId,
    cucsLsServerFsmTaskDn                                            CucsManagedObjectDn,
    cucsLsServerFsmTaskRn                                            SnmpAdminString,
    cucsLsServerFsmTaskCompletion                                    CucsFsmCompletion,
    cucsLsServerFsmTaskFlags                                         CucsLsServerFsmTaskFlags,
    cucsLsServerFsmTaskItem                                          CucsLsServerFsmTaskItem,
    cucsLsServerFsmTaskSeqId                                         Gauge32
}

cucsLsServerFsmTaskInstanceId OBJECT-TYPE
    SYNTAX       CucsManagedObjectId
    MAX-ACCESS   not-accessible
    STATUS       current
    DESCRIPTION
        "Instance identifier of the managed object."
    ::= { cucsLsServerFsmTaskEntry 1 }

cucsLsServerFsmTaskDn OBJECT-TYPE
    SYNTAX       CucsManagedObjectDn
    MAX-ACCESS   read-only
    STATUS       current
    DESCRIPTION
        "Cisco UCS ls:ServerFsmTask:dn managed object property"
    ::= { cucsLsServerFsmTaskEntry 2 }

cucsLsServerFsmTaskRn OBJECT-TYPE
    SYNTAX       SnmpAdminString
    MAX-ACCESS   read-only
    STATUS       current
    DESCRIPTION
        "Cisco UCS ls:ServerFsmTask:rn managed object property"
    ::= { cucsLsServerFsmTaskEntry 3 }

cucsLsServerFsmTaskCompletion OBJECT-TYPE
    SYNTAX       CucsFsmCompletion
    MAX-ACCESS   read-only
    STATUS       current
    DESCRIPTION
        "Cisco UCS ls:ServerFsmTask:completion managed object property"
    ::= { cucsLsServerFsmTaskEntry 4 }

cucsLsServerFsmTaskFlags OBJECT-TYPE
    SYNTAX       CucsLsServerFsmTaskFlags
    MAX-ACCESS   read-only
    STATUS       current
    DESCRIPTION
        "Cisco UCS ls:ServerFsmTask:flags managed object property"
    ::= { cucsLsServerFsmTaskEntry 5 }

cucsLsServerFsmTaskItem OBJECT-TYPE
    SYNTAX       CucsLsServerFsmTaskItem
    MAX-ACCESS   read-only
    STATUS       current
    DESCRIPTION
        "Cisco UCS ls:ServerFsmTask:item managed object property"
    ::= { cucsLsServerFsmTaskEntry 6 }

cucsLsServerFsmTaskSeqId OBJECT-TYPE
    SYNTAX       Gauge32
    MAX-ACCESS   read-only
    STATUS       current
    DESCRIPTION
        "Cisco UCS ls:ServerFsmTask:seqId managed object property"
    ::= { cucsLsServerFsmTaskEntry 7 }

cucsLsTierTable OBJECT-TYPE
    SYNTAX           SEQUENCE OF CucsLsTierEntry
    MAX-ACCESS       not-accessible
    STATUS           current
    DESCRIPTION
        "Cisco UCS ls:Tier managed object table"
    ::= { cucsLsObjects 6 }

cucsLsTierEntry OBJECT-TYPE
    SYNTAX           CucsLsTierEntry
    MAX-ACCESS       not-accessible
    STATUS           current
    DESCRIPTION
        "Entry for the cucsLsTierTable table."
    INDEX { cucsLsTierInstanceId }
    ::= { cucsLsTierTable 1 }

CucsLsTierEntry ::= SEQUENCE {
    cucsLsTierInstanceId                                             CucsManagedObjectId,
    cucsLsTierDn                                                     CucsManagedObjectDn,
    cucsLsTierRn                                                     SnmpAdminString,
    cucsLsTierApply                                                  CucsLsApply,
    cucsLsTierDescr                                                  SnmpAdminString,
    cucsLsTierIntId                                                  SnmpAdminString,
    cucsLsTierName                                                   SnmpAdminString,
    cucsLsTierSrcTemplName                                           SnmpAdminString
}

cucsLsTierInstanceId OBJECT-TYPE
    SYNTAX       CucsManagedObjectId
    MAX-ACCESS   not-accessible
    STATUS       current
    DESCRIPTION
        "Instance identifier of the managed object."
    ::= { cucsLsTierEntry 1 }

cucsLsTierDn OBJECT-TYPE
    SYNTAX       CucsManagedObjectDn
    MAX-ACCESS   read-only
    STATUS       current
    DESCRIPTION
        "Cisco UCS ls:Tier:dn managed object property"
    ::= { cucsLsTierEntry 2 }

cucsLsTierRn OBJECT-TYPE
    SYNTAX       SnmpAdminString
    MAX-ACCESS   read-only
    STATUS       current
    DESCRIPTION
        "Cisco UCS ls:Tier:rn managed object property"
    ::= { cucsLsTierEntry 3 }

cucsLsTierApply OBJECT-TYPE
    SYNTAX       CucsLsApply
    MAX-ACCESS   read-only
    STATUS       current
    DESCRIPTION
        "Cisco UCS ls:Tier:apply managed object property"
    ::= { cucsLsTierEntry 4 }

cucsLsTierDescr OBJECT-TYPE
    SYNTAX       SnmpAdminString
    MAX-ACCESS   read-only
    STATUS       current
    DESCRIPTION
        "Cisco UCS ls:Tier:descr managed object property"
    ::= { cucsLsTierEntry 5 }

cucsLsTierIntId OBJECT-TYPE
    SYNTAX       SnmpAdminString
    MAX-ACCESS   read-only
    STATUS       current
    DESCRIPTION
        "Cisco UCS ls:Tier:intId managed object property"
    ::= { cucsLsTierEntry 6 }

cucsLsTierName OBJECT-TYPE
    SYNTAX       SnmpAdminString
    MAX-ACCESS   read-only
    STATUS       current
    DESCRIPTION
        "Cisco UCS ls:Tier:name managed object property"
    ::= { cucsLsTierEntry 7 }

cucsLsTierSrcTemplName OBJECT-TYPE
    SYNTAX       SnmpAdminString
    MAX-ACCESS   read-only
    STATUS       current
    DESCRIPTION
        "Cisco UCS ls:Tier:srcTemplName managed object property"
    ::= { cucsLsTierEntry 8 }

END
