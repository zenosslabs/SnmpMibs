-- *********************************************************************
-- CISCO-UNIFIED-COMPUTING-ISCSI-MIB.my
-- 
-- MIB representation of the Cisco Unified Computing System
-- ISCSI management information model package
-- 
-- Created September 2011 by Charles Bullis
-- 
-- Copyright (c) 2005-2011 Cisco Systems, Inc. All rights reserved.
-- 
-- *********************************************************************

CISCO-UNIFIED-COMPUTING-ISCSI-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsIscsiProtocolProfileConnectionTimeOut,
    CucsIscsiProtocolProfileDhcpTimeOut,
    CucsIscsiProtocolProfileLunBusyRetryCount
        FROM CISCO-UNIFIED-COMPUTING-TC-MIB;

cucsIscsiObjects MODULE-IDENTITY
    LAST-UPDATED    "201109150000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        ISCSI management information model package"
    ::= { ciscoUnifiedComputingMIBObjects 60 }

cucsIscsiAuthProfileTable OBJECT-TYPE
    SYNTAX           SEQUENCE OF CucsIscsiAuthProfileEntry
    MAX-ACCESS       not-accessible
    STATUS           current
    DESCRIPTION
        "Cisco UCS iscsi:AuthProfile managed object table"
    ::= { cucsIscsiObjects 1 }

cucsIscsiAuthProfileEntry OBJECT-TYPE
    SYNTAX           CucsIscsiAuthProfileEntry
    MAX-ACCESS       not-accessible
    STATUS           current
    DESCRIPTION
        "Entry for the cucsIscsiAuthProfileTable table."
    INDEX { cucsIscsiAuthProfileInstanceId }
    ::= { cucsIscsiAuthProfileTable 1 }

CucsIscsiAuthProfileEntry ::= SEQUENCE {
    cucsIscsiAuthProfileInstanceId                                   CucsManagedObjectId,
    cucsIscsiAuthProfileDn                                           CucsManagedObjectDn,
    cucsIscsiAuthProfileRn                                           SnmpAdminString,
    cucsIscsiAuthProfileDescr                                        SnmpAdminString,
    cucsIscsiAuthProfileIntId                                        SnmpAdminString,
    cucsIscsiAuthProfileName                                         SnmpAdminString,
    cucsIscsiAuthProfilePassword                                     SnmpAdminString,
    cucsIscsiAuthProfileUserId                                       SnmpAdminString
}

cucsIscsiAuthProfileInstanceId OBJECT-TYPE
    SYNTAX       CucsManagedObjectId
    MAX-ACCESS   not-accessible
    STATUS       current
    DESCRIPTION
        "Instance identifier of the managed object."
    ::= { cucsIscsiAuthProfileEntry 1 }

cucsIscsiAuthProfileDn OBJECT-TYPE
    SYNTAX       CucsManagedObjectDn
    MAX-ACCESS   read-only
    STATUS       current
    DESCRIPTION
        "Cisco UCS iscsi:AuthProfile:dn managed object property"
    ::= { cucsIscsiAuthProfileEntry 2 }

cucsIscsiAuthProfileRn OBJECT-TYPE
    SYNTAX       SnmpAdminString
    MAX-ACCESS   read-only
    STATUS       current
    DESCRIPTION
        "Cisco UCS iscsi:AuthProfile:rn managed object property"
    ::= { cucsIscsiAuthProfileEntry 3 }

cucsIscsiAuthProfileDescr OBJECT-TYPE
    SYNTAX       SnmpAdminString
    MAX-ACCESS   read-only
    STATUS       current
    DESCRIPTION
        "Cisco UCS iscsi:AuthProfile:descr managed object property"
    ::= { cucsIscsiAuthProfileEntry 4 }

cucsIscsiAuthProfileIntId OBJECT-TYPE
    SYNTAX       SnmpAdminString
    MAX-ACCESS   read-only
    STATUS       current
    DESCRIPTION
        "Cisco UCS iscsi:AuthProfile:intId managed object property"
    ::= { cucsIscsiAuthProfileEntry 5 }

cucsIscsiAuthProfileName OBJECT-TYPE
    SYNTAX       SnmpAdminString
    MAX-ACCESS   read-only
    STATUS       current
    DESCRIPTION
        "Cisco UCS iscsi:AuthProfile:name managed object property"
    ::= { cucsIscsiAuthProfileEntry 6 }

cucsIscsiAuthProfilePassword OBJECT-TYPE
    SYNTAX       SnmpAdminString
    MAX-ACCESS   read-only
    STATUS       current
    DESCRIPTION
        "Cisco UCS iscsi:AuthProfile:password managed object property"
    ::= { cucsIscsiAuthProfileEntry 7 }

cucsIscsiAuthProfileUserId OBJECT-TYPE
    SYNTAX       SnmpAdminString
    MAX-ACCESS   read-only
    STATUS       current
    DESCRIPTION
        "Cisco UCS iscsi:AuthProfile:userId managed object property"
    ::= { cucsIscsiAuthProfileEntry 8 }

cucsIscsiProtocolProfileTable OBJECT-TYPE
    SYNTAX           SEQUENCE OF CucsIscsiProtocolProfileEntry
    MAX-ACCESS       not-accessible
    STATUS           current
    DESCRIPTION
        "Cisco UCS iscsi:ProtocolProfile managed object table"
    ::= { cucsIscsiObjects 2 }

cucsIscsiProtocolProfileEntry OBJECT-TYPE
    SYNTAX           CucsIscsiProtocolProfileEntry
    MAX-ACCESS       not-accessible
    STATUS           current
    DESCRIPTION
        "Entry for the cucsIscsiProtocolProfileTable table."
    INDEX { cucsIscsiProtocolProfileInstanceId }
    ::= { cucsIscsiProtocolProfileTable 1 }

CucsIscsiProtocolProfileEntry ::= SEQUENCE {
    cucsIscsiProtocolProfileInstanceId                               CucsManagedObjectId,
    cucsIscsiProtocolProfileDn                                       CucsManagedObjectDn,
    cucsIscsiProtocolProfileRn                                       SnmpAdminString,
    cucsIscsiProtocolProfileConnectionTimeOut                        CucsIscsiProtocolProfileConnectionTimeOut,
    cucsIscsiProtocolProfileDescr                                    SnmpAdminString,
    cucsIscsiProtocolProfileDhcpTimeOut                              CucsIscsiProtocolProfileDhcpTimeOut,
    cucsIscsiProtocolProfileIntId                                    SnmpAdminString,
    cucsIscsiProtocolProfileLunBusyRetryCount                        CucsIscsiProtocolProfileLunBusyRetryCount,
    cucsIscsiProtocolProfileName                                     SnmpAdminString,
    cucsIscsiProtocolProfileTcpTimeStamp                             TruthValue
}

cucsIscsiProtocolProfileInstanceId OBJECT-TYPE
    SYNTAX       CucsManagedObjectId
    MAX-ACCESS   not-accessible
    STATUS       current
    DESCRIPTION
        "Instance identifier of the managed object."
    ::= { cucsIscsiProtocolProfileEntry 1 }

cucsIscsiProtocolProfileDn OBJECT-TYPE
    SYNTAX       CucsManagedObjectDn
    MAX-ACCESS   read-only
    STATUS       current
    DESCRIPTION
        "Cisco UCS iscsi:ProtocolProfile:dn managed object property"
    ::= { cucsIscsiProtocolProfileEntry 2 }

cucsIscsiProtocolProfileRn OBJECT-TYPE
    SYNTAX       SnmpAdminString
    MAX-ACCESS   read-only
    STATUS       current
    DESCRIPTION
        "Cisco UCS iscsi:ProtocolProfile:rn managed object property"
    ::= { cucsIscsiProtocolProfileEntry 3 }

cucsIscsiProtocolProfileConnectionTimeOut OBJECT-TYPE
    SYNTAX       CucsIscsiProtocolProfileConnectionTimeOut
    MAX-ACCESS   read-only
    STATUS       current
    DESCRIPTION
        "Cisco UCS iscsi:ProtocolProfile:connectionTimeOut
        managed object property"
    ::= { cucsIscsiProtocolProfileEntry 4 }

cucsIscsiProtocolProfileDescr OBJECT-TYPE
    SYNTAX       SnmpAdminString
    MAX-ACCESS   read-only
    STATUS       current
    DESCRIPTION
        "Cisco UCS iscsi:ProtocolProfile:descr managed object property"
    ::= { cucsIscsiProtocolProfileEntry 5 }

cucsIscsiProtocolProfileDhcpTimeOut OBJECT-TYPE
    SYNTAX       CucsIscsiProtocolProfileDhcpTimeOut
    MAX-ACCESS   read-only
    STATUS       current
    DESCRIPTION
        "Cisco UCS iscsi:ProtocolProfile:dhcpTimeOut managed
        object property"
    ::= { cucsIscsiProtocolProfileEntry 6 }

cucsIscsiProtocolProfileIntId OBJECT-TYPE
    SYNTAX       SnmpAdminString
    MAX-ACCESS   read-only
    STATUS       current
    DESCRIPTION
        "Cisco UCS iscsi:ProtocolProfile:intId managed object property"
    ::= { cucsIscsiProtocolProfileEntry 7 }

cucsIscsiProtocolProfileLunBusyRetryCount OBJECT-TYPE
    SYNTAX       CucsIscsiProtocolProfileLunBusyRetryCount
    MAX-ACCESS   read-only
    STATUS       current
    DESCRIPTION
        "Cisco UCS iscsi:ProtocolProfile:lunBusyRetryCount
        managed object property"
    ::= { cucsIscsiProtocolProfileEntry 8 }

cucsIscsiProtocolProfileName OBJECT-TYPE
    SYNTAX       SnmpAdminString
    MAX-ACCESS   read-only
    STATUS       current
    DESCRIPTION
        "Cisco UCS iscsi:ProtocolProfile:name managed object property"
    ::= { cucsIscsiProtocolProfileEntry 9 }

cucsIscsiProtocolProfileTcpTimeStamp OBJECT-TYPE
    SYNTAX       TruthValue
    MAX-ACCESS   read-only
    STATUS       current
    DESCRIPTION
        "Cisco UCS iscsi:ProtocolProfile:tcpTimeStamp managed
        object property"
    ::= { cucsIscsiProtocolProfileEntry 10 }

END
